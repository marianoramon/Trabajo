AddReference "System.Drawing.Primitives"
AddReference "System.Drawing.Common"
' Las dos lineas de arriba son OBLIGATORIAS y deben quedar las PRIMERAS
' del fichero. Inventor 2026 corre sobre .NET 8, donde System.Drawing
' esta repartido en ensamblados que iLogic no referencia por defecto:
' Size y Color estan en System.Drawing.Primitives, y Font, FontStyle y
' SystemColors en System.Drawing.Common. Sin ellas la regla no compila y
' da "Es necesaria una referencia al ensamblado ... Agregue una al
' proyecto" en cuanto se construye la ventana de resultados.
' =============================================================================
' REGLA iLOGIC: CALCULO_TIEMPO_Y_PESO_LASER
' VERSION: 1.13 REFERENCIAS DE System.Drawing PARA .NET 8
' ENTORNO: Autodesk Inventor 2026
' ALCANCE: METALPLAK - una pieza de chapa IPT activa.
'
' CAMBIOS FRENTE A LA 1.12:
'   La 1.12 no compilaba en Inventor 2026. Al pasar del MessageBox a una
'   ventana propia se empezaron a usar System.Drawing.Size, .Font,
'   .FontStyle y .SystemColors, y en .NET 8 esos tipos viven en
'   ensamblados que iLogic no referencia por defecto. Se anaden las dos
'   directivas AddReference al principio del fichero. No moverlas ni
'   borrarlas.
'
' CAMBIOS FRENTE A LA 1.11:
'   El informe sale ahora en una ventana propia en vez de un MessageBox,
'   que no admite negrita ni tamanos de letra. El detalle completo se
'   mantiene arriba, en un cuadro con scroll, y al pie, justo encima del
'   boton Aceptar, van los dos datos de uso diario en letra grande y
'   negrita: el peso imputado y el tiempo imputado. Debajo de cada uno,
'   en letra pequena, el valor sin redondear del que sale.
'
' CAMBIOS FRENTE A LA 1.10:
'   Calibrado el perfil de 8 mm. 47690 y 67845 son la misma pieza de
'   corte con dos codigos, uno para el corte y otro para el plegado. Con
'   su ficha de 50 s la velocidad pasa de 1900 (acotada) a 2072 mm/min.
'   Con esto quedan calibrados los seis espesores del catalogo.
'
'   La cota fallo aqui mas que en el resto, un 9,1 %, porque se calculo
'   con el perimetro del rectangulo de la pieza, 1118 mm, y el perimetro
'   real es 1439,4 mm: un 29 % de hueco, frente al 4 % de 47689. La cota
'   pierde fuerza en piezas con mucha geometria interior.
'
' AVISO, EL DESARROLLO NO COINCIDE CON EL DE LANTEK:
'   Para esta pieza Inventor da un desarrollo de 122,0 x 439,7 mm y
'   Lantek uno de 119 x 439,662. El largo coincide, pero el ancho difiere
'   en 3,0 mm y el peso neto en un 2,9 % (3,067 kg frente a 2,98 kg).
'   No es redondeo. O el DXF de Lantek viene de una revision anterior, o
'   la tolerancia de plegado de Inventor ya no es la que se uso para
'   generarlo. Conviene revisarlo: afecta a la pieza que sale de maquina,
'   no solo a este calculo. Sobre la calibracion apenas influye, esos
'   3 mm de ancho mueven la velocidad un 0,41 %.
'
' CAMBIOS FRENTE A LA 1.9:
'   Calibrado el perfil de 4 mm con 47689, que en Inventor es la misma
'   pieza que 67844 en Lantek: rectangulo 788x155, peso neto 3,73 kg y
'   rectangular 3,93 kg coinciden en los dos sistemas, solo cambia el
'   codigo. La velocidad pasa de 3400 (acotada) a 3460 mm/min, un 1,8 %.
'
'   En esta version se penso que 47690 y 67845 eran piezas distintas por
'   los 3 mm de diferencia en el ancho del desarrollo. Era una conclusion
'   equivocada: son la misma pieza de corte con dos codigos. Corregido en
'   la 1.11, que calibra 8 mm con su ficha. La diferencia de 3 mm sigue
'   siendo real y esta explicada en el aviso de mas arriba.
'
' CAMBIOS FRENTE A LA 1.8:
'   El adicional de anidado de 10 mm pasa de 7 s (extrapolado) a 5 s
'   (medido). El nesting 28734 de mr04, chapa 1151631516, tarda 21 s
'   frente a los 16 s de ficha de 47691. La serie medida es 4 mm +0 s,
'   6 mm +2 s, 8 mm +5 s y 10 mm +5 s: se estanca, no sigue creciendo.
'   Con esto 47691 queda exacto en los dos tiempos, 15,99 s de ficha y
'   20,99 s de anidado. La misma pagina confirma la densidad por cuarta
'   vez: chapa 3000x1510x10 con 364,67 kg da 8050,1 kg/m3.
'
' CAMBIOS FRENTE A LA 1.7:
'   Se ejecuto la regla sobre las piezas reales y se ajusto la velocidad
'   de cada espesor para que reproduzca su ficha de Lantek. Antes solo
'   3 mm estaba calibrado y con un perimetro supuesto.
'
'     espesor  pieza     v 1.7   v 1.8   desviacion que tenia la 1.7
'       2 mm   A02848     5000    3472         -26,66 %
'       3 mm   A02690     3700    3812          +2,44 %
'       6 mm   47678      2400    2419          +0,73 %
'      10 mm   47691      1750    1789          +1,88 %
'
'   El perimetro que informa Inventor para A02690 es 395,4 mm, el mismo
'   valor que Lantek da como longitud de corte. Es decir, la longitud de
'   Lantek NO incluye las entradas, al contrario de lo que suponia la 1.6.
'   Las entradas siguen en el modelo porque la maquina si las corta y su
'   tiempo esta dentro de la ficha, pero no son comparables con la
'   longitud que informa Lantek. El diagnostico compara ya el perimetro
'   geometrico, no la longitud total.
'
' ESTADO DE LA CALIBRACION:
'   Los seis espesores del catalogo estan calibrados. Cada uno reproduce
'   la ficha de su pieza de referencia con desviacion nula.
'
'     espesor  gas   velocidad   referencia
'       2 mm   N2       3472     A02848, ficha 18 s
'       3 mm   N2       3812     A02690, ficha  8 s
'       4 mm   O2       3460     47689,  ficha 35 s
'       6 mm   O2       2419     47678,  ficha 30 s
'       8 mm   O2       2072     47690,  ficha 50 s
'      10 mm   O2       1789     47691,  ficha 16 s
'
' SOBRE LOS 2 mm:
'   Su velocidad ajustada (3472) queda por DEBAJO de la de 3 mm (3812).
'   No es un error de la tabla. La velocidad de este modelo es efectiva:
'   absorbe las aceleraciones y deceleraciones, que pesan mas cuanto mas
'   fragmentada es la pieza. A02848 son 8 contornos en una chapa de
'   155x80, con 885 mm de perimetro. En una pieza de 2 mm simple este
'   perfil sobreestimara el tiempo. Para separar velocidad de aceleracion
'   hace falta la ficha de una segunda pieza de 2 mm de contorno sencillo.
'
' PENDIENTE DE DATOS:
'   - Por que el desarrollo de 47690 difiere 3 mm del de Lantek.
'   - Ficha de una pieza de 2 mm de contorno simple, para el punto anterior.
'   - Tiempo de nesting de los anidados de 2 mm (chapa 0D1) y 3 mm
'     (chapa 1151575311), unicos adicionales de anidado sin medir.
'   - Suplemento aplicable a la banda 5-10 s, no definido en el criterio.
'   - El criterio de peso rectangulo/2 imputa entre un 18 % y un 47 %
'     menos que el peso neto de Lantek. Es criterio de empresa y no se
'     cambia, pero la regla ya informa de ambos. El peso NETO que calcula
'     la regla si coincide exacto con el de Lantek en las cuatro piezas
'     contrastadas.
' =============================================================================

Sub Main()

    ' ---------------------------------------------------------------------
    ' PESO
    ' ---------------------------------------------------------------------
    ' Densidad confirmada contra el peso de chapa de tres nestings de mr04.
    ' Coincide en los tres al primer decimal, no hay que tocarla.
    Const DENSIDAD_LANTEK_MILDSTEEL_KG_M3 As Double = 8050.0
    ' Criterio de imputacion de empresa. Los datos de mr04 muestran que el
    ' aprovechamiento real del rectangulo va del 64 % al 97 %, nunca 50 %.
    Const DIVISOR_PESO_RECTANGULO As Double = 2.0
    Const PASO_REDONDEO_PESO_KG As Double = 0.05

    ' ---------------------------------------------------------------------
    ' TIEMPO
    ' ---------------------------------------------------------------------
    Const PASO_REDONDEO_TIEMPO_S As Double = 5.0
    ' Pendiente de comprobar en la ficha de la maquina. Un fibra de esta
    ' gama suele mover entre 60000 y 100000 mm/min en rapidos.
    Const VELOCIDAD_RAPIDA_MM_MIN As Double = 18000.0
    Const TOLERANCIA_ESPESOR_MM As Double = 0.15

    Dim documento As Inventor.Document = ThisApplication.ActiveDocument

    If documento Is Nothing Then
        MostrarError("No hay ningun documento activo en Inventor.")
        Exit Sub
    End If

    If documento.DocumentType <> _
       Inventor.DocumentTypeEnum.kPartDocumentObject Then
        MostrarError( _
            "La regla debe ejecutarse desde una pieza IPT de chapa." & _
            vbCrLf & "No calcula ensamblajes IAM ni planos IDW.")
        Exit Sub
    End If

    Dim pieza As Inventor.PartDocument = _
        CType(documento, Inventor.PartDocument)

    Dim chapa As Inventor.SheetMetalComponentDefinition = Nothing
    Try
        chapa = CType( _
            pieza.ComponentDefinition, _
            Inventor.SheetMetalComponentDefinition)
    Catch
        chapa = Nothing
    End Try

    If chapa Is Nothing Then
        MostrarError( _
            "El IPT activo no es una pieza de chapa de Inventor." & _
            vbCrLf & "Convierte o crea la pieza como chapa antes de calcular.")
        Exit Sub
    End If

    Dim codigo As String = ObtenerCodigo(pieza)
    ThisApplication.StatusBarText = _
        "Calculando tiempo y peso laser de " & codigo & "..."

    Try
        If Not pieza.Update2(True) Then
            Throw New Exception( _
                "Inventor no ha podido actualizar completamente la pieza.")
        End If

        If Not chapa.HasFlatPattern Then
            chapa.Unfold()
        End If

        If Not chapa.HasFlatPattern Then
            Throw New Exception( _
                "No se ha podido generar el desarrollo de la pieza.")
        End If

        Dim desarrollo As Inventor.FlatPattern = chapa.FlatPattern
        Try
            desarrollo.ExitEdit()
        Catch
            ' ExitEdit puede fallar si el desarrollo no estaba en edicion.
        End Try

        Dim caraSuperior As Inventor.Face = desarrollo.TopFace
        If caraSuperior Is Nothing Then
            Throw New Exception( _
                "No se ha podido identificar la cara superior del desarrollo.")
        End If

        ' Inventor trabaja internamente en centimetros.
        Dim espesorMm As Double = chapa.Thickness.Value * 10.0
        Dim material As String = LeerPropiedadSeguimiento(pieza, "Material")
        Dim descripcion As String = _
            LeerPropiedadSeguimiento(pieza, "Description")

        If espesorMm <= 0.0 Then
            Throw New Exception( _
                "Inventor ha devuelto un espesor igual o menor que cero.")
        End If

        ' -----------------------------------------------------------------
        ' SELECCION DE PERFIL. Siempre por material y espesor, nunca por
        ' codigo de articulo. Tabla en ObtenerPerfilTecnologia.
        ' -----------------------------------------------------------------
        Dim esAcero As Boolean = EsAceroCarbono(material)

        Dim velocidadCorteMmMin As Double = 0.0
        Dim penetracionS As Double = 0.0
        Dim entradaPorContornoMm As Double = 0.0
        Dim auxiliarAnidadoS As Double = 0.0
        Dim perfilTecnologia As String = ""
        Dim perfilCalibrado As Boolean = False

        ObtenerPerfilTecnologia( _
            esAcero, espesorMm, TOLERANCIA_ESPESOR_MM, _
            velocidadCorteMmMin, penetracionS, entradaPorContornoMm, _
            auxiliarAnidadoS, perfilTecnologia, perfilCalibrado)

        Dim gasCorte As String = ObtenerGasCorte(material, espesorMm)

        ' -----------------------------------------------------------------
        ' GEOMETRIA
        ' -----------------------------------------------------------------
        Dim desarrolloLargoMm As Double = desarrollo.Length * 10.0
        Dim desarrolloAnchoMm As Double = desarrollo.Width * 10.0

        If desarrolloLargoMm <= 0.0 OrElse desarrolloAnchoMm <= 0.0 Then
            Throw New Exception( _
                "Inventor ha devuelto dimensiones de desarrollo no validas.")
        End If

        Dim dimensionMayorMm As Double = _
            Math.Max(desarrolloLargoMm, desarrolloAnchoMm)
        Dim dimensionMenorMm As Double = _
            Math.Min(desarrolloLargoMm, desarrolloAnchoMm)

        Dim perimetroMm As Double = 0.0
        Dim numeroContornos As Integer = 0

        For Each contorno As Inventor.EdgeLoop In caraSuperior.EdgeLoops
            numeroContornos += 1
            For Each arista As Inventor.Edge In contorno.Edges
                perimetroMm += ObtenerLongitudAristaCm(arista) * 10.0
            Next
        Next

        If perimetroMm <= 0.0 OrElse numeroContornos <= 0 Then
            Throw New Exception( _
                "No se ha podido obtener la geometria de corte del desarrollo.")
        End If

        ' Longitud comparable con la que informa Lantek: perimetro geometrico
        ' mas las entradas y salidas de cada contorno.
        Dim longitudEntradasMm As Double = _
            numeroContornos * entradaPorContornoMm
        Dim longitudCorteMm As Double = perimetroMm + longitudEntradasMm

        ' Area neta real de la pieza, para contrastar con el peso de Lantek.
        Dim areaNetaMm2 As Double = ObtenerAreaCaraMm2(caraSuperior)
        Dim areaRectanguloMm2 As Double = dimensionMayorMm * dimensionMenorMm
        Dim aprovechamiento As Double = 0.0
        If areaRectanguloMm2 > 0.0 AndAlso areaNetaMm2 > 0.0 Then
            aprovechamiento = areaNetaMm2 / areaRectanguloMm2
        End If

        ' -----------------------------------------------------------------
        ' PESO
        ' -----------------------------------------------------------------
        Dim densidadKgM3 As Double = 0.0
        Dim origenDensidad As String = ""

        If esAcero Then
            densidadKgM3 = DENSIDAD_LANTEK_MILDSTEEL_KG_M3
            origenDensidad = "Lantek MILDSTEEL/ST37"
        Else
            densidadKgM3 = ObtenerDensidadInventorKgM3(pieza)
            origenDensidad = "material asignado en Inventor"
        End If

        If densidadKgM3 <= 0.0 Then
            Throw New Exception( _
                "No se ha podido obtener una densidad valida para el material.")
        End If

        Dim volumenRectanguloM3 As Double = _
            (dimensionMayorMm / 1000.0) * _
            (dimensionMenorMm / 1000.0) * _
            (espesorMm / 1000.0)
        Dim pesoRectanguloKg As Double = _
            volumenRectanguloM3 * densidadKgM3

        If pesoRectanguloKg <= 0.0 Then
            Throw New Exception( _
                "El peso rectangular calculado es igual o menor que cero.")
        End If

        Dim pesoNetoKg As Double = 0.0
        If areaNetaMm2 > 0.0 Then
            pesoNetoKg = (areaNetaMm2 / 1000000.0) * _
                (espesorMm / 1000.0) * densidadKgM3
        End If

        Dim pesoDivididoKg As Double = _
            pesoRectanguloKg / DIVISOR_PESO_RECTANGULO
        Dim pesoFinalKg As Double = RedondearHaciaArriba( _
            pesoDivididoKg, PASO_REDONDEO_PESO_KG)

        ' -----------------------------------------------------------------
        ' TIEMPO
        ' -----------------------------------------------------------------
        Dim recorridoRapidoMm As Double = _
            EstimarRecorridoRapidoMm(desarrollo, caraSuperior.EdgeLoops)

        Dim tiempoRecorridoCorteS As Double = _
            (longitudCorteMm / velocidadCorteMmMin) * 60.0
        Dim tiempoPenetracionesS As Double = _
            numeroContornos * penetracionS
        Dim tiempoRecorridoRapidoS As Double = _
            (recorridoRapidoMm / VELOCIDAD_RAPIDA_MM_MIN) * 60.0

        Dim tiempoUnidadEstimadoS As Double = _
            tiempoRecorridoCorteS + tiempoPenetracionesS + _
            tiempoRecorridoRapidoS

        Dim tiempoLantekS As Double = _
            tiempoUnidadEstimadoS + auxiliarAnidadoS

        Dim suplementoTiempoS As Double = _
            ObtenerSuplementoTiempo(tiempoLantekS)
        Dim tiempoAntesRedondeoS As Double = _
            tiempoLantekS + suplementoTiempoS
        Dim tiempoFinalS As Double = RedondearHaciaArriba( _
            tiempoAntesRedondeoS, PASO_REDONDEO_TIEMPO_S)

        ' -----------------------------------------------------------------
        ' SALIDA
        ' -----------------------------------------------------------------
        Dim resultado As New System.Text.StringBuilder()

        resultado.AppendLine("CODIGO: " & codigo)
        If descripcion <> "" Then
            resultado.AppendLine("DESCRIPCION: " & descripcion)
        End If
        resultado.AppendLine( _
            "MATERIAL: " & If(material = "", "NO DEFINIDO", material))
        resultado.AppendLine( _
            "ESPESOR: " & Formato(espesorMm, 2) & " mm")
        resultado.AppendLine("GAS: " & gasCorte)
        resultado.AppendLine()

        resultado.AppendLine("PESO RECTANGULAR IMPUTADO A LA PIEZA")
        resultado.AppendLine( _
            "Rectangulo del desarrollo: " & _
            Formato(dimensionMenorMm, 1) & " x " & _
            Formato(dimensionMayorMm, 1) & " mm")
        resultado.AppendLine( _
            "Densidad utilizada: " & Formato(densidadKgM3, 0) & _
            " kg/m3 (" & origenDensidad & ")")
        resultado.AppendLine( _
            "Peso completo del rectangulo: " & _
            Formato(pesoRectanguloKg, 3) & " kg")
        resultado.AppendLine( _
            "Peso dividido entre 2: " & _
            Formato(pesoDivididoKg, 3) & " kg")
        resultado.AppendLine( _
            "PESO FINAL REDONDEADO: " & _
            Formato(pesoFinalKg, 2) & " kg/ud")
        resultado.AppendLine( _
            "Redondeo hacia arriba en pasos de 0,05 kg.")
        resultado.AppendLine()

        resultado.AppendLine("TIEMPO DE CORTE IMPUTADO")
        resultado.AppendLine("Perfil: " & perfilTecnologia)
        resultado.AppendLine( _
            "Velocidad de corte: " & _
            Formato(velocidadCorteMmMin, 0) & " mm/min")
        resultado.AppendLine( _
            "Penetracion por contorno: " & Formato(penetracionS, 2) & " s")
        resultado.AppendLine( _
            "Perimetro geometrico: " & Formato(perimetroMm, 1) & " mm")
        resultado.AppendLine( _
            "Entradas y salidas: " & Formato(longitudEntradasMm, 1) & _
            " mm (" & numeroContornos.ToString() & " x " & _
            Formato(entradaPorContornoMm, 1) & " mm)")
        resultado.AppendLine( _
            "Longitud de corte total: " & Formato(longitudCorteMm, 1) & " mm")
        resultado.AppendLine( _
            "Contornos / penetraciones: " & numeroContornos.ToString())
        resultado.AppendLine( _
            "Desplazamiento rapido estimado: " & _
            Formato(recorridoRapidoMm, 1) & " mm")
        resultado.AppendLine( _
            "Desglose (s): recorrido " & Formato(tiempoRecorridoCorteS, 2) & _
            " + penetraciones " & Formato(tiempoPenetracionesS, 2) & _
            " + rapidos " & Formato(tiempoRecorridoRapidoS, 2))
        resultado.AppendLine( _
            "TIEMPO UNITARIO ESTIMADO (ficha): " & _
            FormatoTiempo(tiempoUnidadEstimadoS))
        Dim tiempoFichaLantekS As Double = ObtenerTiempoFichaLantek(codigo)
        If tiempoFichaLantekS > 0.0 Then
            resultado.AppendLine( _
                "  Ficha real de Lantek (mr04): " & _
                FormatoTiempo(tiempoFichaLantekS))
            resultado.AppendLine( _
                "  Desviacion de la regla: " & _
                FormatoConSigno(tiempoUnidadEstimadoS - tiempoFichaLantekS) & _
                " s (" & _
                FormatoConSigno( _
                    (tiempoUnidadEstimadoS - tiempoFichaLantekS) / _
                    tiempoFichaLantekS * 100.0) & " %)")
        End If
        resultado.AppendLine( _
            "Adicional de anidado estimado: " & FormatoTiempo(auxiliarAnidadoS))
        resultado.AppendLine( _
            "TIEMPO BASE ESTIMADO (anidado): " & FormatoTiempo(tiempoLantekS))
        resultado.AppendLine( _
            "Suplemento aplicado: +" & _
            Formato(suplementoTiempoS, 0) & " s")
        resultado.AppendLine( _
            "Antes de redondear: " & FormatoTiempo(tiempoAntesRedondeoS))
        resultado.AppendLine( _
            "TIEMPO FINAL REDONDEADO: " & FormatoTiempo(tiempoFinalS))
        resultado.AppendLine()
        resultado.AppendLine( _
            "Criterio: hasta 5 s suma 1; de 5 a 30 s suma 5; " & _
            "mas de 30 s suma 10; despues redondea hacia arriba cada 5 s.")
        resultado.AppendLine()

        ' -----------------------------------------------------------------
        ' DIAGNOSTICO: magnitudes a contrastar contra la ficha de Lantek.
        ' -----------------------------------------------------------------
        resultado.AppendLine("DIAGNOSTICO PARA CONTRASTAR CON LANTEK")
        If areaNetaMm2 > 0.0 Then
            resultado.AppendLine( _
                "Area neta de la pieza: " & _
                Formato(areaNetaMm2 / 100.0, 1) & " cm2")
            resultado.AppendLine( _
                "Aprovechamiento del rectangulo: " & _
                Formato(aprovechamiento * 100.0, 1) & " %")
            resultado.AppendLine( _
                "Peso NETO real de la pieza: " & _
                Formato(pesoNetoKg, 3) & " kg")
            resultado.AppendLine( _
                "Si Lantek informa el peso neto, comparalo con esta linea," & _
                " no con el peso imputado.")
        Else
            resultado.AppendLine( _
                "No se ha podido medir el area neta de la cara superior.")
        End If
        resultado.AppendLine( _
            "Comprueba que Lantek indique " & numeroContornos.ToString() & _
            " perforaciones y una longitud de corte proxima a " & _
            Formato(perimetroMm, 1) & " mm.")
        resultado.AppendLine( _
            "La longitud que informa Lantek es el perimetro geometrico," & _
            " sin las entradas.")
        resultado.AppendLine( _
            "Si el numero de contornos no coincide, la cara superior del" & _
            " desarrollo tiene aristas de particion o falta geometria.")
        If Not perfilCalibrado Then
            resultado.AppendLine()
            resultado.AppendLine( _
                "AVISO: este perfil NO tiene calibracion validada. El tiempo" & _
                " es orientativo. El unico punto medido es acero 3 mm/N2.")
        End If

        ThisApplication.StatusBarText = _
            "Calculo laser completado para " & codigo & "."

        MostrarResultado( _
            "CALCULO LASER - " & codigo, _
            resultado.ToString(), _
            pesoDivididoKg, pesoFinalKg, _
            tiempoAntesRedondeoS, tiempoFinalS)

    Catch ex As Exception
        ThisApplication.StatusBarText = _
            "Error en calculo laser de " & codigo & "."
        MostrarError( _
            "No se ha podido completar el calculo." & _
            vbCrLf & vbCrLf & ex.Message)
    End Try

End Sub

Private Sub MostrarResultado( _
    ByVal titulo As String, _
    ByVal detalle As String, _
    ByVal pesoDivididoKg As Double, _
    ByVal pesoFinalKg As Double, _
    ByVal tiempoAntesRedondeoS As Double, _
    ByVal tiempoFinalS As Double)

    ' Ventana propia en lugar de MessageBox: hace falta para poder sacar
    ' el resumen del pie en negrita y con letra mas grande.

    Dim formulario As System.Windows.Forms.Form = Nothing

    Try
        Dim anclaInferior As System.Windows.Forms.AnchorStyles = _
            System.Windows.Forms.AnchorStyles.Bottom Or _
            System.Windows.Forms.AnchorStyles.Left Or _
            System.Windows.Forms.AnchorStyles.Right

        formulario = New System.Windows.Forms.Form()
        formulario.Text = titulo
        formulario.ClientSize = New System.Drawing.Size(580, 720)
        formulario.MinimumSize = New System.Drawing.Size(540, 520)
        formulario.StartPosition = _
            System.Windows.Forms.FormStartPosition.CenterScreen
        formulario.MaximizeBox = False
        formulario.MinimizeBox = False
        formulario.ShowInTaskbar = False

        Dim cuadroDetalle As New System.Windows.Forms.TextBox()
        cuadroDetalle.Multiline = True
        cuadroDetalle.ReadOnly = True
        cuadroDetalle.WordWrap = False
        cuadroDetalle.ScrollBars = System.Windows.Forms.ScrollBars.Both
        cuadroDetalle.Font = New System.Drawing.Font("Consolas", 9.0!)
        cuadroDetalle.Text = detalle
        cuadroDetalle.SetBounds(10, 10, 560, 540)
        cuadroDetalle.Anchor = _
            System.Windows.Forms.AnchorStyles.Top Or anclaInferior

        Dim separador As New System.Windows.Forms.Label()
        separador.BorderStyle = System.Windows.Forms.BorderStyle.Fixed3D
        separador.SetBounds(10, 558, 560, 2)
        separador.Anchor = anclaInferior

        Dim fuenteResumen As New System.Drawing.Font( _
            "Segoe UI", 16.0!, System.Drawing.FontStyle.Bold)
        Dim fuenteDetalleResumen As New System.Drawing.Font( _
            "Segoe UI", 8.5!)

        Dim etiquetaPeso As New System.Windows.Forms.Label()
        etiquetaPeso.Font = fuenteResumen
        etiquetaPeso.Text = _
            "PESO:  " & Formato(pesoFinalKg, 2) & " kg/ud"
        etiquetaPeso.SetBounds(10, 566, 560, 34)
        etiquetaPeso.Anchor = anclaInferior

        Dim etiquetaPesoDetalle As New System.Windows.Forms.Label()
        etiquetaPesoDetalle.Font = fuenteDetalleResumen
        etiquetaPesoDetalle.ForeColor = System.Drawing.SystemColors.GrayText
        etiquetaPesoDetalle.Text = _
            "rectangulo / 2 = " & Formato(pesoDivididoKg, 3) & _
            " kg, redondeado hacia arriba a 0,05"
        etiquetaPesoDetalle.SetBounds(12, 600, 558, 16)
        etiquetaPesoDetalle.Anchor = anclaInferior

        Dim etiquetaTiempo As New System.Windows.Forms.Label()
        etiquetaTiempo.Font = fuenteResumen
        etiquetaTiempo.Text = _
            "TIEMPO:  " & FormatoTiempoCorto(tiempoFinalS)
        etiquetaTiempo.SetBounds(10, 620, 560, 34)
        etiquetaTiempo.Anchor = anclaInferior

        Dim etiquetaTiempoDetalle As New System.Windows.Forms.Label()
        etiquetaTiempoDetalle.Font = fuenteDetalleResumen
        etiquetaTiempoDetalle.ForeColor = System.Drawing.SystemColors.GrayText
        etiquetaTiempoDetalle.Text = _
            "corte + suplemento = " & Formato(tiempoAntesRedondeoS, 2) & _
            " s, redondeado hacia arriba a 5 s"
        etiquetaTiempoDetalle.SetBounds(12, 654, 558, 16)
        etiquetaTiempoDetalle.Anchor = anclaInferior

        Dim botonAceptar As New System.Windows.Forms.Button()
        botonAceptar.Text = "Aceptar"
        botonAceptar.DialogResult = System.Windows.Forms.DialogResult.OK
        botonAceptar.SetBounds(490, 678, 80, 30)
        botonAceptar.Anchor = _
            System.Windows.Forms.AnchorStyles.Bottom Or _
            System.Windows.Forms.AnchorStyles.Right

        formulario.Controls.Add(cuadroDetalle)
        formulario.Controls.Add(separador)
        formulario.Controls.Add(etiquetaPeso)
        formulario.Controls.Add(etiquetaPesoDetalle)
        formulario.Controls.Add(etiquetaTiempo)
        formulario.Controls.Add(etiquetaTiempoDetalle)
        formulario.Controls.Add(botonAceptar)

        formulario.AcceptButton = botonAceptar
        formulario.CancelButton = botonAceptar

        ' El cursor arranca al principio del informe, no seleccionandolo.
        cuadroDetalle.Select(0, 0)
        botonAceptar.Select()

        formulario.ShowDialog()

    Catch
        ' Si el formulario falla por lo que sea, el informe no se pierde.
        System.Windows.Forms.MessageBox.Show( _
            detalle, titulo, _
            System.Windows.Forms.MessageBoxButtons.OK, _
            System.Windows.Forms.MessageBoxIcon.Information)
    Finally
        If formulario IsNot Nothing Then formulario.Dispose()
    End Try

End Sub

Private Function FormatoTiempoCorto(ByVal segundos As Double) As String
    If segundos < 0.0 Then segundos = 0.0

    Dim total As Integer = _
        CInt(Math.Round( _
            segundos, 0, System.MidpointRounding.AwayFromZero))

    If total < 60 Then Return total.ToString() & " s"

    Return (total \ 60).ToString() & " min " & _
        (total Mod 60).ToString("00") & " s"
End Function

Private Sub ObtenerPerfilTecnologia( _
    ByVal esAcero As Boolean, _
    ByVal espesorMm As Double, _
    ByVal toleranciaMm As Double, _
    ByRef velocidadMmMin As Double, _
    ByRef penetracionS As Double, _
    ByRef entradaMm As Double, _
    ByRef adicionalAnidadoS As Double, _
    ByRef descripcion As String, _
    ByRef calibrado As Boolean)

    ' Catalogo de tecnologias de DURMA FIBRA 4 METROS - MILDSTEEL ST37,
    ' segun el explorador de anidados del trabajo mr04.
    '
    '   espesor  gas usado          pieza de referencia   ficha
    '     2 mm   Nitrogen-120       A02848 155x80          18 s
    '     3 mm   Nitrogen-120       A02690 131x25           8 s
    '     4 mm   Oxygen-212         67844  788x155         35 s
    '     6 mm   Oxygen-212         47678  490x62          30 s
    '     8 mm   Oxygen-212         67845  440x119         50 s
    '    10 mm   Oxygen-212         47691  55x175          16 s
    '
    ' Solo 3 mm esta calibrado: su velocidad se despeja de la ficha de
    ' A02690 descontando penetraciones y rapidos.
    '   t_corte = 8 - 4 * 0,30 - (116,5 / 18000 * 60) = 6,4117 s
    '   v_ef    = 395,4 / 6,4117 * 60 = 3700 mm/min
    '
    ' El resto son valores ACOTADOS, no medidos. La cota inferior de cada
    ' uno es el perimetro del rectangulo de su pieza de referencia dividido
    ' entre el tiempo de ficha. Como la longitud real de corte es mayor que
    ' ese perimetro, la velocidad real es algo mayor que la cota. Los
    ' valores elegidos respetan la cota y son monotonos decrecientes con el
    ' espesor, que es lo minimo que debe cumplir el modelo.
    '
    '   espesor  cota inferior   tabla   origen
    '     2 mm     1567            3472   ajustado a A02848 (18 s)
    '     3 mm     2340            3812   ajustado a A02690 (8 s)
    '     4 mm     3233            3460   ajustado a 47689 (35 s)
    '     6 mm     2208            2419   ajustado a 47678 (30 s)
    '     8 mm     1342            2072   ajustado a 47690 (50 s)
    '    10 mm     1725            1789   ajustado a 47691 (16 s)
    '
    ' El adicional de anidado esta medido comparando ficha y nesting en
    ' mr04: 4 mm +0 s, 6 mm +2 s, 8 mm +5 s, 10 mm +5 s. La serie no
    ' crece indefinidamente, se estanca en 5 s. Los de 2 y 3 mm siguen
    ' sin medir; se asumen 0 s, coherente con el +0 s medido a 4 mm.

    ' Perfil de reserva para cualquier espesor fuera del catalogo.
    velocidadMmMin = 2500.0
    penetracionS = 1.0
    entradaMm = 4.0
    adicionalAnidadoS = 2.0
    descripcion = "Reserva, espesor fuera del catalogo, SIN CALIBRAR"
    calibrado = False

    If Not esAcero Then
        descripcion = "Reserva, material no reconocido, SIN CALIBRAR"
        Exit Sub
    End If

    If Math.Abs(espesorMm - 2.0) <= toleranciaMm Then
        velocidadMmMin = 3472.0
        penetracionS = 0.15
        entradaMm = 3.0
        adicionalAnidadoS = 0.0
        descripcion = "2 mm/N2, CALIBRADO con A02848 (ficha 18 s)"
        calibrado = True
        Exit Sub
    End If

    If Math.Abs(espesorMm - 3.0) <= toleranciaMm Then
        velocidadMmMin = 3812.0
        penetracionS = 0.3
        entradaMm = 3.0
        adicionalAnidadoS = 0.0
        descripcion = "3 mm/N2, CALIBRADO con A02690 (ficha 8 s)"
        calibrado = True
        Exit Sub
    End If

    If Math.Abs(espesorMm - 4.0) <= toleranciaMm Then
        velocidadMmMin = 3460.0
        penetracionS = 0.5
        entradaMm = 4.0
        adicionalAnidadoS = 0.0
        descripcion = "4 mm/O2, CALIBRADO con 47689 (ficha 35 s)"
        calibrado = True
        Exit Sub
    End If

    If Math.Abs(espesorMm - 6.0) <= toleranciaMm Then
        velocidadMmMin = 2419.0
        penetracionS = 0.8
        entradaMm = 5.0
        adicionalAnidadoS = 2.0
        descripcion = "6 mm/O2, CALIBRADO con 47678 (ficha 30 s)"
        calibrado = True
        Exit Sub
    End If

    If Math.Abs(espesorMm - 8.0) <= toleranciaMm Then
        velocidadMmMin = 2072.0
        penetracionS = 1.2
        entradaMm = 5.0
        adicionalAnidadoS = 5.0
        descripcion = "8 mm/O2, CALIBRADO con 47690 (ficha 50 s)"
        calibrado = True
        Exit Sub
    End If

    If Math.Abs(espesorMm - 10.0) <= toleranciaMm Then
        velocidadMmMin = 1789.0
        penetracionS = 2.0
        entradaMm = 6.0
        adicionalAnidadoS = 5.0
        descripcion = "10 mm/O2, CALIBRADO con 47691 (ficha 16 s)"
        calibrado = True
        Exit Sub
    End If

End Sub

Private Function ObtenerTiempoFichaLantek( _
    ByVal codigo As String) As Double

    ' Tiempo de corte unitario que informa el listado de elementos de
    ' trabajo de mr04, en segundos. Sirve para que la regla informe de su
    ' propia desviacion al calcular una de las piezas de referencia.
    ' No interviene en el calculo.

    If String.IsNullOrWhiteSpace(codigo) Then Return 0.0

    Select Case codigo.Trim().ToUpperInvariant()
        Case "A02848"
            Return 18.0
        Case "A02690"
            Return 8.0
        Case "67844", "47689"
            ' 47689 en Inventor es la misma pieza que 67844 en Lantek:
            ' rectangulo 788x155, peso neto 3,73 kg y rectangular 3,93 kg
            ' coinciden en ambos. Solo cambia el codigo.
            Return 35.0
        Case "47678"
            Return 30.0
        Case "67845", "47690"
            ' Misma pieza de corte con dos codigos: 47690 es el del corte
            ' y 67845 el del plegado. El desarrollo difiere 3 mm en ancho
            ' entre Inventor y Lantek, ver la cabecera.
            Return 50.0
        Case "47691"
            Return 16.0
    End Select

    Return 0.0
End Function

Private Function ObtenerAreaCaraMm2(ByVal cara As Inventor.Face) As Double
    If cara Is Nothing Then Return 0.0

    Try
        ' SurfaceEvaluator.Area devuelve centimetros cuadrados.
        Return Math.Abs(cara.Evaluator.Area) * 100.0
    Catch
        Return 0.0
    End Try
End Function

Private Function ObtenerLongitudAristaCm( _
    ByVal arista As Inventor.Edge) As Double

    If arista Is Nothing Then Return 0.0

    Dim evaluador As Inventor.CurveEvaluator = arista.Evaluator
    Dim parametroMinimo As Double = 0.0
    Dim parametroMaximo As Double = 0.0
    Dim longitudCm As Double = 0.0

    evaluador.GetParamExtents(parametroMinimo, parametroMaximo)
    evaluador.GetLengthAtParam( _
        parametroMinimo, parametroMaximo, longitudCm)

    Return Math.Abs(longitudCm)
End Function

Private Function ObtenerPuntoMedioArista( _
    ByVal arista As Inventor.Edge) As Inventor.Point

    If arista Is Nothing Then Return Nothing

    Try
        Dim evaluador As Inventor.CurveEvaluator = arista.Evaluator
        Dim parametroMinimo As Double = 0.0
        Dim parametroMaximo As Double = 0.0
        evaluador.GetParamExtents(parametroMinimo, parametroMaximo)

        Dim parametroMedio As Double = _
            (parametroMinimo + parametroMaximo) / 2.0
        Dim parametros() As Double = {parametroMedio}
        Dim coordenadas(2) As Double
        evaluador.GetPointAtParam(parametros, coordenadas)

        Return ThisApplication.TransientGeometry.CreatePoint( _
            coordenadas(0), coordenadas(1), coordenadas(2))
    Catch
        Return Nothing
    End Try
End Function

Private Function EstimarRecorridoRapidoMm( _
    ByVal desarrollo As Inventor.FlatPattern, _
    ByVal contornos As Inventor.EdgeLoops) As Double

    Dim puntos As New System.Collections.Generic.List(Of Inventor.Point)

    For Each contorno As Inventor.EdgeLoop In contornos
        If contorno.Edges.Count > 0 Then
            Dim punto As Inventor.Point = _
                ObtenerPuntoMedioArista(contorno.Edges.Item(1))
            If punto IsNot Nothing Then puntos.Add(punto)
        End If
    Next

    If puntos.Count = 0 Then Return 0.0

    Dim minimo As Inventor.Point = desarrollo.RangeBox.MinPoint
    Dim puntoActual As Inventor.Point = _
        ThisApplication.TransientGeometry.CreatePoint( _
            minimo.X, minimo.Y, minimo.Z)
    Dim distanciaTotalCm As Double = 0.0

    While puntos.Count > 0
        Dim indiceMasCercano As Integer = 0
        Dim distanciaMasCercana As Double = _
            puntoActual.DistanceTo(puntos(0))

        For i As Integer = 1 To puntos.Count - 1
            Dim distancia As Double = puntoActual.DistanceTo(puntos(i))
            If distancia < distanciaMasCercana Then
                distanciaMasCercana = distancia
                indiceMasCercano = i
            End If
        Next

        distanciaTotalCm += distanciaMasCercana
        puntoActual = puntos(indiceMasCercano)
        puntos.RemoveAt(indiceMasCercano)
    End While

    Return distanciaTotalCm * 10.0
End Function

Private Function EsAceroCarbono(ByVal material As String) As Boolean
    If String.IsNullOrWhiteSpace(material) Then Return False

    Dim texto As String = material.Trim().ToUpperInvariant()

    If texto.Contains("STAINLESS") OrElse _
       texto.Contains("INOX") Then
        Return False
    End If

    Return texto.Contains("MILDSTEEL") OrElse _
           texto.Contains("MILD STEEL") OrElse _
           texto.Contains("ST37") OrElse _
           texto.Contains("S235") OrElse _
           texto.Contains("S355") OrElse _
           texto.Contains("ACERO")
End Function

Private Function ObtenerGasCorte( _
    ByVal material As String, _
    ByVal espesorMm As Double) As String

    If String.IsNullOrWhiteSpace(material) Then
        Return "NO DETERMINADO"
    End If

    Dim texto As String = material.Trim().ToUpperInvariant()

    If EsAceroCarbono(material) Then
        If espesorMm < 4.0 Then
            Return "NITROGENO"
        End If
        Return "OXIGENO"
    End If

    If texto.Contains("STAINLESS") OrElse _
       texto.Contains("INOX") Then
        Return "NITROGENO"
    End If

    If texto.Contains("COPPER") OrElse _
       texto.Contains("COBRE") Then
        Return "OXIGENO"
    End If

    If texto.Contains("ALUMIN") Then
        Return "NITROGENO"
    End If

    Return "NO DETERMINADO"
End Function

Private Function ObtenerDensidadInventorKgM3( _
    ByVal pieza As Inventor.PartDocument) As Double

    Try
        Dim propiedades As Inventor.MassProperties = _
            pieza.ComponentDefinition.MassProperties

        If propiedades Is Nothing Then Return 0.0
        If propiedades.Mass <= 0.0 OrElse propiedades.Volume <= 0.0 Then
            Return 0.0
        End If

        ' Masa interna en kg y volumen interno en cm3.
        Return propiedades.Mass / (propiedades.Volume / 1000000.0)
    Catch
        Return 0.0
    End Try
End Function

Private Function ObtenerSuplementoTiempo( _
    ByVal tiempoLantekS As Double) As Double

    ' El criterio original dejaba sin definir la banda de 5 a 10 s y los
    ' valores exactos 5, 10 y 30 s, que caian a suplemento cero. Aqui la
    ' escalera cubre todo el dominio y es monotona.
    ' CONFIRMAR: la banda 5-10 s se ha asignado a +5 s. Si en produccion
    ' debe ser +1 s, cambiar la primera condicion a 5,0 -> 10,0.
    If tiempoLantekS <= 5.0 Then Return 1.0
    If tiempoLantekS <= 30.0 Then Return 5.0

    Return 10.0
End Function

Private Function RedondearHaciaArriba( _
    ByVal valor As Double, _
    ByVal paso As Double) As Double

    If valor <= 0.0 OrElse paso <= 0.0 Then Return 0.0

    ' La resta minima evita subir otro paso por ruido de coma flotante
    ' cuando el valor ya es un multiplo exacto.
    Return Math.Ceiling((valor / paso) - 0.000000001) * paso
End Function

Private Function LeerPropiedadSeguimiento( _
    ByVal documento As Inventor.Document, _
    ByVal nombrePropiedad As String) As String

    Try
        Dim conjunto As Inventor.PropertySet = _
            documento.PropertySets.Item("Design Tracking Properties")
        Dim propiedad As Inventor.Property = conjunto.Item(nombrePropiedad)

        If propiedad Is Nothing OrElse propiedad.Value Is Nothing Then
            Return ""
        End If

        Return CStr(propiedad.Value).Trim()
    Catch
        Return ""
    End Try
End Function

Private Function ObtenerCodigo( _
    ByVal documento As Inventor.Document) As String

    Dim nombre As String = ""

    Try
        If Not String.IsNullOrWhiteSpace(documento.FullFileName) Then
            nombre = System.IO.Path.GetFileNameWithoutExtension( _
                documento.FullFileName)
        End If
    Catch
    End Try

    If String.IsNullOrWhiteSpace(nombre) Then
        nombre = System.IO.Path.GetFileNameWithoutExtension( _
            documento.DisplayName)
    End If

    If String.IsNullOrWhiteSpace(nombre) Then Return "SIN_CODIGO"

    Dim limpio As String = nombre.Trim()
    Dim separadores() As Char = {" "c, "-"c}
    Dim posicion As Integer = limpio.IndexOfAny(separadores)

    If posicion > 0 Then
        limpio = limpio.Substring(0, posicion)
    End If

    Return limpio.Trim().ToUpperInvariant()
End Function

Private Function Formato( _
    ByVal valor As Double, _
    ByVal decimales As Integer) As String

    Return valor.ToString( _
        "N" & decimales.ToString(), _
        System.Globalization.CultureInfo.CurrentCulture)
End Function

Private Function FormatoConSigno(ByVal valor As Double) As String
    If valor > 0.0 Then
        Return "+" & Formato(valor, 2)
    End If

    Return Formato(valor, 2)
End Function

Private Function FormatoTiempo(ByVal segundos As Double) As String
    If segundos < 0.0 Then segundos = 0.0

    Dim segundosRedondeados As Integer = _
        CInt(Math.Round( _
            segundos, _
            0, _
            System.MidpointRounding.AwayFromZero))
    Dim minutos As Integer = segundosRedondeados \ 60
    Dim restoSegundos As Integer = segundosRedondeados Mod 60

    Return minutos.ToString() & " min " & _
        restoSegundos.ToString("00") & " s" & _
        " (" & Formato(segundos, 2) & " s)"
End Function

Private Sub MostrarError(ByVal mensaje As String)
    System.Windows.Forms.MessageBox.Show( _
        mensaje, _
        "CALCULO TIEMPO Y PESO LASER - METALPLAK", _
        System.Windows.Forms.MessageBoxButtons.OK, _
        System.Windows.Forms.MessageBoxIcon.Error)
End Sub
