' =====================================================================
'  BUSCADOR DE FICHEROS EN LA RED (con INDICE)  -  Regla iLogic Inventor
' =====================================================================
'
'  Funcionamiento:
'    1) INDEXAR: recorre una vez la carpeta de red y guarda un fichero
'       indice (IndiceBuscador.txt) en la carpeta que tu indiques.
'    2) BUSCAR: las busquedas leen ese indice -> casi instantaneas.
'
'  Modos de indexado:
'    - Rapido (solo nombre): en SEGUNDO PLANO, no congela Inventor.
'    - Completo (nombre + Nº de pieza): lee la iProperty "Part Number" con
'      el Apprentice Server. Va en el hilo principal (con progreso y
'      Cancelar) porque la API de Inventor no admite hilos.
'
'  Reindexado INCREMENTAL: reutiliza el Nº de pieza de los ficheros que no
'  han cambiado (no los vuelve a leer).  Opcion "Actualizar al abrir".
'
'  Se indexan piezas (.ipt), ensamblajes (.iam) y planos (.idw). Se
'  EXCLUYEN las copias de seguridad de Inventor (carpeta "OldVersions"). La
'  busqueda compara el codigo con el NOMBRE del fichero y con el Nº DE PIEZA.
'
'  NOTA: iLogic auto-importa el namespace "Inventor" (choca con Application,
'  View, TextBox, Environment...). Por eso TODO va cualificado con su ruta
'  completa (System.Windows.Forms..., System...).
' =====================================================================

Sub Main()
    Dim frm As New BuscadorFicherosForm(ThisApplication)
    frm.ShowDialog()
End Sub


Public Class BuscadorFicherosForm
    Inherits System.Windows.Forms.Form

    ' Valores por defecto. EDITA estas lineas si cambian tus rutas.
    Private Const RUTA_DEFECTO As String = "P:\"
    Private Const RUTA_RED As String = "\\192.168.10.217\DISEÑO"
    Private Const MAX_RESULTADOS As Integer = 2000

    Private oApp As Inventor.Application

    Private txtRuta As System.Windows.Forms.TextBox
    Private btnExaminar As System.Windows.Forms.Button
    Private cboUnidad As System.Windows.Forms.ComboBox
    Private txtIndice As System.Windows.Forms.TextBox
    Private btnExaminarIndice As System.Windows.Forms.Button
    Private chkPartNumber As System.Windows.Forms.CheckBox
    Private btnIndexar As System.Windows.Forms.Button
    Private btnActualizar As System.Windows.Forms.Button
    Private lblIndiceInfo As System.Windows.Forms.Label
    Private txtCodigo As System.Windows.Forms.TextBox
    Private rdoTodos As System.Windows.Forms.RadioButton
    Private rdoPiezas As System.Windows.Forms.RadioButton
    Private rdoEnsamblajes As System.Windows.Forms.RadioButton
    Private rdoPlanos As System.Windows.Forms.RadioButton
    Private btnBuscar As System.Windows.Forms.Button
    Private btnCancelar As System.Windows.Forms.Button
    Private btnAbrir As System.Windows.Forms.Button
    Private btnAbrirCarpeta As System.Windows.Forms.Button
    Private lstResultados As System.Windows.Forms.ListView
    Private lblEstado As System.Windows.Forms.Label

    Private hiloTrabajo As System.Threading.Thread
    Private cancelar As Boolean = False
    Private _cuentaIndexada As Integer = 0
    Private _progreso As Integer = 0
    Private _nPiezas As Integer = 0
    Private _nEnsam As Integer = 0
    Private _nPlanos As Integer = 0
    Private _errorTrabajo As String = ""

    ' Indice en memoria (cache). Entrada: {ruta, nombreLower, extLower, ticks, pnLower}.
    Private _indice As System.Collections.Generic.List(Of String())
    Private _indiceFirma As String = ""

    Public Sub New(app As Inventor.Application)
        oApp = app
        InicializarComponentes()
    End Sub

    Private Function CarpetaConfig() As String
        Return System.IO.Path.Combine( _
            System.Environment.GetFolderPath(System.Environment.SpecialFolder.MyDocuments), _
            "BuscadorInventor")
    End Function

    Private Sub InicializarComponentes()
        Me.Text = "Buscar ficheros en la red (con indice)"
        Me.Width = 800
        Me.Height = 700
        Me.StartPosition = System.Windows.Forms.FormStartPosition.CenterScreen

        Dim anchTLR As System.Windows.Forms.AnchorStyles = _
            System.Windows.Forms.AnchorStyles.Top _
            Or System.Windows.Forms.AnchorStyles.Left _
            Or System.Windows.Forms.AnchorStyles.Right
        Dim anchTR As System.Windows.Forms.AnchorStyles = _
            System.Windows.Forms.AnchorStyles.Top Or System.Windows.Forms.AnchorStyles.Right

        ' --- Fila 1: carpeta a indexar ---
        Me.Controls.Add(Etiqueta("Carpeta a indexar:", 12, 15, 130))
        txtRuta = New System.Windows.Forms.TextBox()
        txtRuta.Left = 145 : txtRuta.Top = 12 : txtRuta.Width = 490 : txtRuta.Anchor = anchTLR
        Me.Controls.Add(txtRuta)
        btnExaminar = Boton("Examinar...", 660, 10, 115, 26, anchTR)
        AddHandler btnExaminar.Click, AddressOf OnExaminarRuta
        Me.Controls.Add(btnExaminar)

        ' --- Fila 2: unidad rapida ---
        Me.Controls.Add(Etiqueta("Unidad:", 12, 47, 130))
        cboUnidad = New System.Windows.Forms.ComboBox()
        cboUnidad.Left = 145 : cboUnidad.Top = 44 : cboUnidad.Width = 280
        cboUnidad.DropDownStyle = System.Windows.Forms.ComboBoxStyle.DropDownList
        cboUnidad.Items.Add("Ruta de red (" & RUTA_RED & ")")
        Try
            For Each unidad As String In System.Environment.GetLogicalDrives()
                cboUnidad.Items.Add(unidad)
            Next
        Catch
        End Try
        AddHandler cboUnidad.SelectedIndexChanged, AddressOf OnUnidadChanged
        Me.Controls.Add(cboUnidad)

        ' --- Fila 3: carpeta del indice ---
        Me.Controls.Add(Etiqueta("Carpeta del indice:", 12, 81, 130))
        txtIndice = New System.Windows.Forms.TextBox()
        txtIndice.Left = 145 : txtIndice.Top = 78 : txtIndice.Width = 490 : txtIndice.Anchor = anchTLR
        AddHandler txtIndice.TextChanged, AddressOf OnIndiceCarpetaChanged
        Me.Controls.Add(txtIndice)
        btnExaminarIndice = Boton("Examinar...", 660, 76, 115, 26, anchTR)
        AddHandler btnExaminarIndice.Click, AddressOf OnExaminarIndice
        Me.Controls.Add(btnExaminarIndice)

        ' --- Fila 4: opciones de indexado ---
        chkPartNumber = New System.Windows.Forms.CheckBox()
        chkPartNumber.Text = "Indexar tambien Nº de pieza (mas lento)"
        chkPartNumber.Left = 145 : chkPartNumber.Top = 110 : chkPartNumber.Width = 290
        Me.Controls.Add(chkPartNumber)

        ' --- Fila 5: indexar + info ---
        btnIndexar = Boton("Indexar todo", 145, 138, 115, 28, _
            System.Windows.Forms.AnchorStyles.Top Or System.Windows.Forms.AnchorStyles.Left)
        AddHandler btnIndexar.Click, AddressOf OnIndexar
        Me.Controls.Add(btnIndexar)
        btnActualizar = Boton("Actualizar", 265, 138, 115, 28, _
            System.Windows.Forms.AnchorStyles.Top Or System.Windows.Forms.AnchorStyles.Left)
        AddHandler btnActualizar.Click, AddressOf OnActualizar
        Me.Controls.Add(btnActualizar)
        lblIndiceInfo = Etiqueta("", 388, 143, 390)
        Me.Controls.Add(lblIndiceInfo)

        ' --- Fila 6: codigo + buscar ---
        Me.Controls.Add(Etiqueta("Codigo a buscar:", 12, 179, 130))
        txtCodigo = New System.Windows.Forms.TextBox()
        txtCodigo.Left = 145 : txtCodigo.Top = 176 : txtCodigo.Width = 490 : txtCodigo.Anchor = anchTLR
        AddHandler txtCodigo.KeyDown, AddressOf OnCodigoKeyDown
        Me.Controls.Add(txtCodigo)
        btnBuscar = Boton("Buscar", 660, 174, 115, 26, anchTR)
        AddHandler btnBuscar.Click, AddressOf OnBuscar
        Me.Controls.Add(btnBuscar)

        ' --- Fila 7: filtro por tipo ---
        rdoTodos = New System.Windows.Forms.RadioButton()
        rdoTodos.Text = "Todos" : rdoTodos.Checked = True
        rdoTodos.Left = 145 : rdoTodos.Top = 208 : rdoTodos.Width = 70
        Me.Controls.Add(rdoTodos)
        rdoPiezas = New System.Windows.Forms.RadioButton()
        rdoPiezas.Text = "Piezas (.ipt)"
        rdoPiezas.Left = 220 : rdoPiezas.Top = 208 : rdoPiezas.Width = 110
        Me.Controls.Add(rdoPiezas)
        rdoEnsamblajes = New System.Windows.Forms.RadioButton()
        rdoEnsamblajes.Text = "Ensamblajes (.iam)"
        rdoEnsamblajes.Left = 335 : rdoEnsamblajes.Top = 208 : rdoEnsamblajes.Width = 150
        Me.Controls.Add(rdoEnsamblajes)
        rdoPlanos = New System.Windows.Forms.RadioButton()
        rdoPlanos.Text = "Planos (.idw)"
        rdoPlanos.Left = 490 : rdoPlanos.Top = 208 : rdoPlanos.Width = 160
        Me.Controls.Add(rdoPlanos)

        ' --- Lista de resultados ---
        lstResultados = New System.Windows.Forms.ListView()
        lstResultados.Left = 12 : lstResultados.Top = 238
        lstResultados.Width = 763 : lstResultados.Height = 372
        lstResultados.View = System.Windows.Forms.View.Details
        lstResultados.FullRowSelect = True
        lstResultados.MultiSelect = False
        lstResultados.Anchor = System.Windows.Forms.AnchorStyles.Top _
            Or System.Windows.Forms.AnchorStyles.Bottom _
            Or System.Windows.Forms.AnchorStyles.Left _
            Or System.Windows.Forms.AnchorStyles.Right
        lstResultados.Columns.Add("Nombre", 220)
        lstResultados.Columns.Add("Nº pieza", 110)
        lstResultados.Columns.Add("Tipo", 60)
        lstResultados.Columns.Add("Modificado", 115)
        lstResultados.Columns.Add("Ruta", 250)
        AddHandler lstResultados.DoubleClick, AddressOf OnAbrir
        Me.Controls.Add(lstResultados)

        ' --- Estado + botones ---
        lblEstado = Etiqueta("Listo.", 12, 624, 300)
        lblEstado.Anchor = System.Windows.Forms.AnchorStyles.Bottom Or System.Windows.Forms.AnchorStyles.Left
        Me.Controls.Add(lblEstado)
        btnCancelar = Boton("Cancelar", 318, 619, 100, 30, _
            System.Windows.Forms.AnchorStyles.Bottom Or System.Windows.Forms.AnchorStyles.Right)
        btnCancelar.Enabled = False
        AddHandler btnCancelar.Click, AddressOf OnCancelar
        Me.Controls.Add(btnCancelar)
        btnAbrirCarpeta = Boton("Abrir carpeta", 425, 619, 160, 30, _
            System.Windows.Forms.AnchorStyles.Bottom Or System.Windows.Forms.AnchorStyles.Right)
        AddHandler btnAbrirCarpeta.Click, AddressOf OnAbrirCarpeta
        Me.Controls.Add(btnAbrirCarpeta)
        btnAbrir = Boton("Abrir en Inventor", 592, 619, 183, 30, _
            System.Windows.Forms.AnchorStyles.Bottom Or System.Windows.Forms.AnchorStyles.Right)
        AddHandler btnAbrir.Click, AddressOf OnAbrir
        Me.Controls.Add(btnAbrir)

        Me.AcceptButton = btnBuscar

        CargarAjustes()
        ActualizarInfoIndice()
    End Sub

    ' --- Helpers de creacion de controles ---
    Private Function Etiqueta(texto As String, x As Integer, y As Integer, w As Integer) _
            As System.Windows.Forms.Label
        Dim l As New System.Windows.Forms.Label()
        l.Text = texto : l.Left = x : l.Top = y : l.Width = w
        Return l
    End Function

    Private Function Boton(texto As String, x As Integer, y As Integer, w As Integer, _
            h As Integer, anchor As System.Windows.Forms.AnchorStyles) As System.Windows.Forms.Button
        Dim b As New System.Windows.Forms.Button()
        b.Text = texto : b.Left = x : b.Top = y : b.Width = w : b.Height = h : b.Anchor = anchor
        Return b
    End Function

    ' --- Ajustes (recordar rutas y opciones) ---
    Private Function ArchivoAjustes() As String
        Return System.IO.Path.Combine(CarpetaConfig(), "ajustes.txt")
    End Function

    Private Sub CargarAjustes()
        Dim ruta As String = RUTA_DEFECTO
        Dim indice As String = CarpetaConfig()
        Dim pn As Boolean = False
        Try
            Dim a As String = ArchivoAjustes()
            If System.IO.File.Exists(a) Then
                Dim ls() As String = System.IO.File.ReadAllLines(a)
                If ls.Length >= 1 AndAlso ls(0).Trim() <> "" Then ruta = ls(0).Trim()
                If ls.Length >= 2 AndAlso ls(1).Trim() <> "" Then indice = ls(1).Trim()
                If ls.Length >= 3 Then pn = (ls(2).Trim() = "1")
            End If
        Catch
        End Try
        txtRuta.Text = ruta
        txtIndice.Text = indice
        chkPartNumber.Checked = pn
    End Sub

    Private Sub GuardarAjustes()
        Try
            System.IO.Directory.CreateDirectory(CarpetaConfig())
            System.IO.File.WriteAllText(ArchivoAjustes(), _
                txtRuta.Text.Trim() & vbCrLf & txtIndice.Text.Trim() & vbCrLf & _
                If(chkPartNumber.Checked, "1", "0") & vbCrLf)
        Catch
        End Try
    End Sub

    Private Function CarpetaIndice() As String
        Dim carpeta As String = txtIndice.Text.Trim()
        If carpeta = "" Then carpeta = CarpetaConfig()
        Return carpeta
    End Function

    ' Convierte una ruta en un nombre de fichero valido.
    Private Function Sanitizar(s As String) As String
        Dim r As String = s
        For Each c As Char In System.IO.Path.GetInvalidFileNameChars()
            r = r.Replace(c, "_"c)
        Next
        r = r.Replace(" ", "_")
        If r.Length > 80 Then r = r.Substring(0, 80)
        If r = "" Then r = "raiz"
        Return r
    End Function

    ' Fichero de indice para la carpeta a indexar ACTUAL (una por unidad).
    Private Function ArchivoIndiceActual() As String
        Return System.IO.Path.Combine(CarpetaIndice(), _
            "IndiceBuscador_" & Sanitizar(txtRuta.Text.Trim()) & ".txt")
    End Function

    ' TODOS los ficheros de indice de la carpeta (la busqueda usa todos).
    Private Function ListarArchivosIndice() As System.Collections.Generic.List(Of String)
        Dim res As New System.Collections.Generic.List(Of String)
        Try
            Dim carpeta As String = CarpetaIndice()
            If System.IO.Directory.Exists(carpeta) Then
                For Each f As String In System.IO.Directory.GetFiles(carpeta, "IndiceBuscador*.txt")
                    res.Add(f)
                Next
            End If
        Catch
        End Try
        Return res
    End Function

    ' Lee la carpeta raiz que se indexo (de la cabecera del fichero).
    Private Function RaizDeIndice(archivo As String) As String
        Try
            Using sr As New System.IO.StreamReader(archivo)
                Dim primera As String = sr.ReadLine()
                If primera IsNot Nothing AndAlso primera.StartsWith("#") Then
                    Dim p() As String = primera.Split(CChar(vbTab))
                    If p.Length >= 3 Then Return p(2)
                End If
            End Using
        Catch
        End Try
        Return System.IO.Path.GetFileNameWithoutExtension(archivo)
    End Function

    Private Sub ActualizarInfoIndice()
        Try
            Dim archivos = ListarArchivosIndice()
            If archivos.Count = 0 Then
                lblIndiceInfo.Text = "Sin indice. Pulsa 'Indexar ahora'."
                Return
            End If
            Dim ultima As Date = Date.MinValue
            Dim raices As New System.Collections.Generic.List(Of String)
            For Each a As String In archivos
                Dim f As Date = System.IO.File.GetLastWriteTime(a)
                If f > ultima Then ultima = f
                raices.Add(RaizDeIndice(a))
            Next
            lblIndiceInfo.Text = archivos.Count.ToString() & " indice(s): " & _
                String.Join(", ", raices.ToArray()) & "  (ult. " & ultima.ToString("yyyy-MM-dd HH:mm") & ")"
        Catch
            lblIndiceInfo.Text = ""
        End Try
    End Sub

    ' --- Eventos de rutas ---
    Private Sub OnExaminarRuta(sender As Object, e As System.EventArgs)
        Dim r As String = ElegirCarpeta(txtRuta.Text)
        If r <> "" Then txtRuta.Text = r
    End Sub

    Private Sub OnExaminarIndice(sender As Object, e As System.EventArgs)
        Dim r As String = ElegirCarpeta(txtIndice.Text)
        If r <> "" Then txtIndice.Text = r
    End Sub

    Private Function ElegirCarpeta(inicial As String) As String
        Dim dlg As New System.Windows.Forms.FolderBrowserDialog()
        dlg.Description = "Elige la carpeta"
        Try
            If System.IO.Directory.Exists(inicial.Trim()) Then dlg.SelectedPath = inicial.Trim()
        Catch
        End Try
        If dlg.ShowDialog() = System.Windows.Forms.DialogResult.OK Then Return dlg.SelectedPath
        Return ""
    End Function

    Private Sub OnUnidadChanged(sender As Object, e As System.EventArgs)
        If cboUnidad.SelectedIndex = 0 Then
            txtRuta.Text = RUTA_RED
        ElseIf cboUnidad.SelectedIndex > 0 Then
            txtRuta.Text = cboUnidad.SelectedItem.ToString()
        End If
    End Sub

    Private Sub OnIndiceCarpetaChanged(sender As Object, e As System.EventArgs)
        ActualizarInfoIndice()
    End Sub

    Private Sub OnCodigoKeyDown(sender As Object, e As System.Windows.Forms.KeyEventArgs)
        If e.KeyCode = System.Windows.Forms.Keys.Enter Then
            OnBuscar(sender, e)
            e.SuppressKeyPress = True
        End If
    End Sub

    ' ================= INDEXACION =================
    ' "Indexar todo": reconstruye el indice desde cero (relee todo, incluido Nº pieza).
    Private Sub OnIndexar(sender As Object, e As System.EventArgs)
        LanzarIndexado(False)
    End Sub

    ' "Actualizar": incremental. Solo procesa ficheros nuevos o modificados;
    ' los que no han cambiado conservan su entrada (no se relee el Nº de pieza).
    Private Sub OnActualizar(sender As Object, e As System.EventArgs)
        Dim archivo As String = ArchivoIndiceActual()
        If Not System.IO.File.Exists(archivo) Then
            Dim resp As System.Windows.Forms.DialogResult = System.Windows.Forms.MessageBox.Show( _
                "Todavia no hay indice de esta carpeta, asi que se hara un indexado completo." & _
                vbCrLf & vbCrLf & "¿Continuar?", "Actualizar indice", _
                System.Windows.Forms.MessageBoxButtons.YesNo, _
                System.Windows.Forms.MessageBoxIcon.Question)
            If resp <> System.Windows.Forms.DialogResult.Yes Then Return
        End If
        LanzarIndexado(True)
    End Sub

    Private Sub LanzarIndexado(incremental As Boolean)
        If hiloTrabajo IsNot Nothing AndAlso hiloTrabajo.IsAlive Then Return

        Dim ruta As String = txtRuta.Text.Trim()
        If ruta = "" OrElse Not System.IO.Directory.Exists(ruta) Then
            System.Windows.Forms.MessageBox.Show("La carpeta a indexar no existe:" & vbCrLf & ruta, _
                "Indexar", System.Windows.Forms.MessageBoxButtons.OK, _
                System.Windows.Forms.MessageBoxIcon.Warning)
            Return
        End If

        Dim carpetaIndice As String = txtIndice.Text.Trim()
        If carpetaIndice = "" Then carpetaIndice = CarpetaConfig()
        Try
            System.IO.Directory.CreateDirectory(carpetaIndice)
        Catch ex As System.Exception
            System.Windows.Forms.MessageBox.Show("No se pudo usar la carpeta del indice:" & vbCrLf & _
                ex.Message, "Indexar", System.Windows.Forms.MessageBoxButtons.OK, _
                System.Windows.Forms.MessageBoxIcon.Error)
            Return
        End Try

        GuardarAjustes()
        cancelar = False
        btnIndexar.Enabled = False
        btnActualizar.Enabled = False
        btnBuscar.Enabled = False
        btnCancelar.Enabled = True
        Me.Cursor = System.Windows.Forms.Cursors.WaitCursor

        Dim archivo As String = ArchivoIndiceActual()
        Dim accion As String
        If incremental Then
            accion = "Actualizando"
        Else
            accion = "Indexando"
        End If

        ' Ambos modos se ejecutan en SEGUNDO PLANO: puedes cerrar la ventana
        ' y seguir trabajando en Inventor; el indice se sigue creando.
        If chkPartNumber.Checked Then
            lblEstado.Text = accion & " con Nº de pieza en segundo plano (puedes cerrar y seguir trabajando)..."
            hiloTrabajo = New System.Threading.Thread(Sub() EjecutarIndexadoCompleto(ruta, archivo, incremental))
        Else
            lblEstado.Text = accion & " en segundo plano (puedes cerrar y seguir trabajando): " & ruta & " ..."
            hiloTrabajo = New System.Threading.Thread(Sub() EjecutarIndexadoRapido(ruta, archivo, incremental))
        End If
        hiloTrabajo.IsBackground = True
        ' STA: necesario para usar COM (Apprentice Server) desde el hilo.
        Try
            hiloTrabajo.SetApartmentState(System.Threading.ApartmentState.STA)
        Catch
        End Try
        hiloTrabajo.Start()
    End Sub

    ' Lee el indice existente a un diccionario  ruta -> {ticks, partnumber}.
    Private Function CargarIndiceDiccionario(archivo As String) _
            As System.Collections.Generic.Dictionary(Of String, String())
        Dim d As New System.Collections.Generic.Dictionary(Of String, String())( _
            System.StringComparer.OrdinalIgnoreCase)
        Try
            If System.IO.File.Exists(archivo) Then
                For Each l As String In System.IO.File.ReadAllLines(archivo)
                    If l = "" OrElse l.StartsWith("#") Then Continue For
                    Dim p() As String = l.Split(CChar(vbTab))
                    If p.Length < 2 Then Continue For
                    Dim pn As String = ""
                    If p.Length >= 3 Then pn = p(2)
                    d(p(0)) = New String() {p(1), pn}
                Next
            End If
        Catch
        End Try
        Return d
    End Function

    Private Sub EscribirEntrada(sw As System.IO.StreamWriter, ruta As String, _
            ticks As Long, pn As String)
        Dim ext As String = System.IO.Path.GetExtension(ruta).ToLower()
        If ext = ".ipt" Then
            _nPiezas += 1
        ElseIf ext = ".iam" Then
            _nEnsam += 1
        ElseIf ext = ".idw" Then
            _nPlanos += 1
        End If
        Dim pnLimpio As String = pn.Replace(vbTab, " ").Replace(vbCr, " ").Replace(vbLf, " ")
        sw.WriteLine(ruta & vbTab & ticks.ToString() & vbTab & pnLimpio)
    End Sub

    ' --- Indexado RAPIDO (segundo plano, solo nombre; reutiliza Nº pieza previo) ---
    Private Sub EjecutarIndexadoRapido(ruta As String, archivo As String, incremental As Boolean)
        _cuentaIndexada = 0
        _progreso = 0
        _nPiezas = 0
        _nEnsam = 0
        _nPlanos = 0
        _errorTrabajo = ""
        ' En "Indexar todo" se ignora el indice previo (diccionario vacio);
        ' en "Actualizar" se reutiliza el Nº de pieza de los ficheros sin cambios.
        Dim viejo As System.Collections.Generic.Dictionary(Of String, String())
        If incremental Then
            viejo = CargarIndiceDiccionario(archivo)
        Else
            viejo = New System.Collections.Generic.Dictionary(Of String, String())( _
                System.StringComparer.OrdinalIgnoreCase)
        End If
        Try
            Using sw As New System.IO.StreamWriter(archivo, False, System.Text.Encoding.UTF8)
                sw.WriteLine("#INDICE" & vbTab & System.DateTime.Now.ToString("yyyy-MM-dd HH:mm") & vbTab & ruta)
                _cuentaIndexada = IndexarRapido(ruta, sw, viejo)
            End Using
        Catch ex As System.Exception
            _errorTrabajo = ex.Message
        End Try
        _indice = Nothing
        Try
            If Me.IsHandleCreated AndAlso Not Me.IsDisposed Then
                Me.Invoke(New System.Action(AddressOf FinIndexado))
            End If
        Catch
        End Try
    End Sub

    Private Function IndexarRapido(carpeta As String, sw As System.IO.StreamWriter, _
            viejo As System.Collections.Generic.Dictionary(Of String, String())) As Integer
        If cancelar Then Return 0
        Dim n As Integer = 0
        Dim ficheros() As String = Nothing
        Try
            ficheros = System.IO.Directory.GetFiles(carpeta)
        Catch
            Return 0
        End Try
        For Each f As String In ficheros
            If cancelar Then Return n
            Dim ext As String = System.IO.Path.GetExtension(f).ToLower()
            If EsIndexable(ext) Then
                Dim ticks As Long = 0
                Try
                    ticks = System.IO.File.GetLastWriteTime(f).Ticks
                Catch
                End Try
                ' Reutiliza Nº de pieza previo si el fichero no ha cambiado.
                Dim pn As String = ""
                Dim prev() As String = Nothing
                If viejo.TryGetValue(f, prev) AndAlso prev(0) = ticks.ToString() Then pn = prev(1)
                EscribirEntrada(sw, f, ticks, pn)
                n += 1
                _progreso += 1
                If (_progreso Mod 200) = 0 Then ActualizarProgresoAsync()
            End If
        Next
        Dim subs() As String = Nothing
        Try
            subs = System.IO.Directory.GetDirectories(carpeta)
        Catch
            Return n
        End Try
        For Each sc As String In subs
            If EsCarpetaExcluida(sc) Then Continue For
            n += IndexarRapido(sc, sw, viejo)
            If cancelar Then Return n
        Next
        Return n
    End Function

    ' Actualiza el contador en la UI desde el hilo de fondo (no bloqueante).
    Private Sub ActualizarProgresoAsync()
        Try
            If Me.IsHandleCreated AndAlso Not Me.IsDisposed Then
                Me.BeginInvoke(New System.Action(AddressOf MostrarProgreso))
            End If
        Catch
        End Try
    End Sub

    Private Sub MostrarProgreso()
        lblEstado.Text = "Indexando... " & _progreso.ToString() & " ficheros"
    End Sub

    ' --- Indexado COMPLETO (segundo plano, lee Nº de pieza con Apprentice) ---
    Private Sub EjecutarIndexadoCompleto(ruta As String, archivo As String, incremental As Boolean)
        _cuentaIndexada = 0
        _progreso = 0
        _nPiezas = 0
        _nEnsam = 0
        _nPlanos = 0
        _errorTrabajo = ""
        ' "Indexar todo" relee el Nº de pieza de TODOS los ficheros (diccionario vacio);
        ' "Actualizar" solo lo lee de los ficheros nuevos o modificados.
        Dim viejo As System.Collections.Generic.Dictionary(Of String, String())
        If incremental Then
            viejo = CargarIndiceDiccionario(archivo)
        Else
            viejo = New System.Collections.Generic.Dictionary(Of String, String())( _
                System.StringComparer.OrdinalIgnoreCase)
        End If

        Dim oApr As Inventor.ApprenticeServerComponent = Nothing
        Try
            oApr = New Inventor.ApprenticeServerComponent()
        Catch
            oApr = Nothing  ' sin Apprentice: se indexa solo el nombre
        End Try

        Try
            Using sw As New System.IO.StreamWriter(archivo, False, System.Text.Encoding.UTF8)
                sw.WriteLine("#INDICE" & vbTab & System.DateTime.Now.ToString("yyyy-MM-dd HH:mm") & vbTab & ruta & vbTab & "PN")
                _cuentaIndexada = IndexarCompleto(ruta, sw, viejo, oApr)
            End Using
        Catch ex As System.Exception
            _errorTrabajo = ex.Message
        End Try

        oApr = Nothing
        _indice = Nothing
        Try
            If Me.IsHandleCreated AndAlso Not Me.IsDisposed Then
                Me.Invoke(New System.Action(AddressOf FinIndexado))
            End If
        Catch
        End Try
    End Sub

    Private Function IndexarCompleto(carpeta As String, sw As System.IO.StreamWriter, _
            viejo As System.Collections.Generic.Dictionary(Of String, String()), _
            oApr As Inventor.ApprenticeServerComponent) As Integer
        If cancelar Then Return 0
        Dim n As Integer = 0
        Dim ficheros() As String = Nothing
        Try
            ficheros = System.IO.Directory.GetFiles(carpeta)
        Catch
            Return 0
        End Try
        For Each f As String In ficheros
            If cancelar Then Return n
            Dim ext As String = System.IO.Path.GetExtension(f).ToLower()
            If EsIndexable(ext) Then
                Dim ticks As Long = 0
                Try
                    ticks = System.IO.File.GetLastWriteTime(f).Ticks
                Catch
                End Try

                Dim pn As String = ""
                Dim prev() As String = Nothing
                If viejo.TryGetValue(f, prev) AndAlso prev(0) = ticks.ToString() Then
                    pn = prev(1)  ' sin cambios: reutiliza (no relee la iProperty)
                ElseIf oApr IsNot Nothing Then
                    pn = LeerNumeroPieza(oApr, f)
                End If

                EscribirEntrada(sw, f, ticks, pn)
                n += 1
                _progreso += 1
                If (_progreso Mod 20) = 0 Then ActualizarProgresoAsync()
            End If
        Next
        Dim subs() As String = Nothing
        Try
            subs = System.IO.Directory.GetDirectories(carpeta)
        Catch
            Return n
        End Try
        For Each sc As String In subs
            If EsCarpetaExcluida(sc) Then Continue For
            n += IndexarCompleto(sc, sw, viejo, oApr)
            If cancelar Then Return n
        Next
        Return n
    End Function

    ' Lee la iProperty "Part Number" sin abrir el fichero en pantalla.
    Private Function LeerNumeroPieza(oApr As Inventor.ApprenticeServerComponent, ruta As String) As String
        Dim pn As String = ""
        Try
            Dim oDoc As Inventor.ApprenticeServerDocument = oApr.Open(ruta)
            Try
                Dim v As Object = oDoc.PropertySets.Item("Design Tracking Properties").Item("Part Number").Value
                If v IsNot Nothing Then pn = v.ToString()
            Catch
            End Try
            Try
                oApr.Close()
            Catch
            End Try
        Catch
            Try
                oApr.Close()
            Catch
            End Try
        End Try
        Return pn
    End Function

    Private Sub FinIndexado()
        Me.Cursor = System.Windows.Forms.Cursors.Default
        btnIndexar.Enabled = True
        btnActualizar.Enabled = True
        btnBuscar.Enabled = True
        btnCancelar.Enabled = False
        ActualizarInfoIndice()

        If _errorTrabajo <> "" Then
            lblEstado.Text = "Error al indexar: " & _errorTrabajo
        ElseIf cancelar Then
            lblEstado.Text = "Indexacion cancelada (" & _cuentaIndexada.ToString() & " ficheros)."
        Else
            lblEstado.Text = "Indice creado: " & _cuentaIndexada.ToString() & " ficheros (" & _
                _nPiezas.ToString() & " piezas, " & _nEnsam.ToString() & " ensamblajes, " & _
                _nPlanos.ToString() & " planos)."
        End If
    End Sub

    ' ================= BUSQUEDA (sobre el indice) =================
    Private Function ExtensionesActivas() As System.Collections.Generic.List(Of String)
        Dim exts As New System.Collections.Generic.List(Of String)
        If rdoPiezas.Checked Then
            exts.Add(".ipt")
        ElseIf rdoEnsamblajes.Checked Then
            exts.Add(".iam")
        ElseIf rdoPlanos.Checked Then
            exts.Add(".idw")
        Else
            exts.Add(".ipt")
            exts.Add(".iam")
            exts.Add(".idw")
        End If
        Return exts
    End Function

    ' Tipos que se indexan: piezas, ensamblajes y planos.
    Private Function EsIndexable(ext As String) As Boolean
        Return ext = ".ipt" OrElse ext = ".iam" OrElse ext = ".idw"
    End Function

    ' Carpetas a excluir (copias de seguridad de Inventor).
    Private Function EsCarpetaExcluida(carpeta As String) As Boolean
        Dim nombre As String = System.IO.Path.GetFileName(carpeta.TrimEnd("\"c))
        Return String.Equals(nombre, "OldVersions", System.StringComparison.OrdinalIgnoreCase)
    End Function

    ' True si la ruta es una copia de seguridad de Inventor (carpeta OldVersions).
    Private Function EsCopiaSeguridad(ruta As String) As Boolean
        Return ruta.ToLower().Contains("\oldversions\")
    End Function

    ' Firma de los indices (rutas + fechas) para saber si hay que recargar.
    Private Function FirmaIndices(archivos As System.Collections.Generic.List(Of String)) As String
        Dim sb As New System.Text.StringBuilder()
        For Each a As String In archivos
            sb.Append(a).Append("|")
            Try
                sb.Append(System.IO.File.GetLastWriteTime(a).Ticks)
            Catch
            End Try
            sb.Append(";")
        Next
        Return sb.ToString()
    End Function

    ' Carga TODOS los ficheros de indice en memoria (con cache y sin duplicados).
    Private Function CargarIndices(archivos As System.Collections.Generic.List(Of String)) As Boolean
        Try
            Dim firma As String = FirmaIndices(archivos)
            If _indice IsNot Nothing AndAlso _indiceFirma = firma Then Return True

            Dim lista As New System.Collections.Generic.List(Of String())
            Dim vistos As New System.Collections.Generic.HashSet(Of String)( _
                System.StringComparer.OrdinalIgnoreCase)

            For Each archivo As String In archivos
                For Each l As String In System.IO.File.ReadAllLines(archivo)
                    If l = "" OrElse l.StartsWith("#") Then Continue For
                    Dim p() As String = l.Split(CChar(vbTab))
                    If p.Length < 2 Then Continue For
                    Dim ruta As String = p(0)
                    If vistos.Contains(ruta) Then Continue For
                    vistos.Add(ruta)
                    Dim nombre As String = System.IO.Path.GetFileNameWithoutExtension(ruta).ToLower()
                    Dim ext As String = System.IO.Path.GetExtension(ruta).ToLower()
                    Dim pnLower As String = ""
                    If p.Length >= 3 Then pnLower = p(2).ToLower()
                    lista.Add(New String() {ruta, nombre, ext, p(1), pnLower})
                Next
            Next

            _indice = lista
            _indiceFirma = firma
            Return True
        Catch
            Return False
        End Try
    End Function

    Private Sub OnBuscar(sender As Object, e As System.EventArgs)
        Dim codigo As String = txtCodigo.Text.Trim()
        If codigo = "" Then
            System.Windows.Forms.MessageBox.Show("Escribe un codigo para buscar.", "Buscador", _
                System.Windows.Forms.MessageBoxButtons.OK, _
                System.Windows.Forms.MessageBoxIcon.Information)
            Return
        End If

        Dim archivos = ListarArchivosIndice()
        If archivos.Count = 0 Then
            Dim resp As System.Windows.Forms.DialogResult = System.Windows.Forms.MessageBox.Show( _
                "No hay ningun indice en esa carpeta." & vbCrLf & vbCrLf & "¿Indexar ahora?", _
                "Buscador", System.Windows.Forms.MessageBoxButtons.YesNo, _
                System.Windows.Forms.MessageBoxIcon.Question)
            If resp = System.Windows.Forms.DialogResult.Yes Then OnIndexar(sender, e)
            Return
        End If

        lblEstado.Text = "Buscando en " & archivos.Count.ToString() & " indice(s)..."
        Me.Cursor = System.Windows.Forms.Cursors.WaitCursor
        Me.Refresh()

        If Not CargarIndices(archivos) Then
            Me.Cursor = System.Windows.Forms.Cursors.Default
            System.Windows.Forms.MessageBox.Show("No se pudieron leer los indices.", _
                "Buscador", System.Windows.Forms.MessageBoxButtons.OK, _
                System.Windows.Forms.MessageBoxIcon.Error)
            Return
        End If

        Dim exts As System.Collections.Generic.List(Of String) = ExtensionesActivas()
        Dim cod As String = codigo.ToLower()
        Dim encontrados As New System.Collections.Generic.List(Of String())
        Dim truncado As Boolean = False

        For Each entrada As String() In _indice
            If EsCopiaSeguridad(entrada(0)) Then Continue For
            If exts.Contains(entrada(2)) Then
                Dim coincide As Boolean = entrada(1).Contains(cod)
                If Not coincide AndAlso entrada(4) <> "" Then coincide = entrada(4).Contains(cod)
                If coincide Then
                    encontrados.Add(entrada)
                    If encontrados.Count >= MAX_RESULTADOS Then
                        truncado = True
                        Exit For
                    End If
                End If
            End If
        Next

        encontrados.Sort(Function(a, b) CLng(b(3)).CompareTo(CLng(a(3))))

        lstResultados.Items.Clear()
        For Each entrada As String() In encontrados
            Dim ruta As String = entrada(0)
            Dim item As New System.Windows.Forms.ListViewItem(System.IO.Path.GetFileName(ruta))
            item.SubItems.Add(entrada(4))  ' Nº pieza (en minusculas tal cual se indexo)
            item.SubItems.Add(entrada(2).ToUpper().Replace(".", ""))
            Dim fechaStr As String = ""
            Try
                fechaStr = New System.DateTime(CLng(entrada(3))).ToString("yyyy-MM-dd HH:mm")
            Catch
            End Try
            item.SubItems.Add(fechaStr)
            item.SubItems.Add(ruta)
            item.Tag = ruta
            lstResultados.Items.Add(item)
        Next

        Me.Cursor = System.Windows.Forms.Cursors.Default
        Dim msg As String = encontrados.Count.ToString() & " resultado(s) para """ & codigo & """."
        If truncado Then msg &= " (limitado a " & MAX_RESULTADOS & ")"
        lblEstado.Text = msg

        If lstResultados.Items.Count > 0 Then
            lstResultados.Items(0).Selected = True
            lstResultados.Select()
        End If
    End Sub

    Private Sub OnCancelar(sender As Object, e As System.EventArgs)
        cancelar = True
        lblEstado.Text = "Cancelando..."
        btnCancelar.Enabled = False
    End Sub

    Private Function RutaSeleccionada() As String
        If lstResultados.SelectedItems.Count = 0 Then
            System.Windows.Forms.MessageBox.Show("Selecciona un fichero de la lista.", "Buscador", _
                System.Windows.Forms.MessageBoxButtons.OK, _
                System.Windows.Forms.MessageBoxIcon.Information)
            Return ""
        End If
        Dim ruta As String = lstResultados.SelectedItems(0).Tag.ToString()
        If Not System.IO.File.Exists(ruta) Then
            System.Windows.Forms.MessageBox.Show("El fichero ya no existe (reindexa):" & vbCrLf & ruta, _
                "Buscador", System.Windows.Forms.MessageBoxButtons.OK, _
                System.Windows.Forms.MessageBoxIcon.Warning)
            Return ""
        End If
        Return ruta
    End Function

    Private Sub OnAbrir(sender As Object, e As System.EventArgs)
        Dim ruta As String = RutaSeleccionada()
        If ruta = "" Then Return
        Try
            oApp.Documents.Open(ruta, True)
            Me.Close()
        Catch ex As System.Exception
            System.Windows.Forms.MessageBox.Show("No se pudo abrir el fichero:" & vbCrLf & ruta & _
                vbCrLf & vbCrLf & ex.Message, "Error al abrir", _
                System.Windows.Forms.MessageBoxButtons.OK, _
                System.Windows.Forms.MessageBoxIcon.Error)
        End Try
    End Sub

    ' Abre el Explorador de Windows con el fichero seleccionado.
    Private Sub OnAbrirCarpeta(sender As Object, e As System.EventArgs)
        Dim ruta As String = RutaSeleccionada()
        If ruta = "" Then Return
        Try
            System.Diagnostics.Process.Start("explorer.exe", "/select,""" & ruta & """")
        Catch ex As System.Exception
            System.Windows.Forms.MessageBox.Show("No se pudo abrir el Explorador:" & vbCrLf & _
                ex.Message, "Abrir carpeta", System.Windows.Forms.MessageBoxButtons.OK, _
                System.Windows.Forms.MessageBoxIcon.Error)
        End Try
    End Sub

End Class
