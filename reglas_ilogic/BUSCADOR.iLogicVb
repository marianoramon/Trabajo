' =====================================================================
'  BUSCADOR CAD - INDICE DE BUSQUEDA - v7.9.2
' =====================================================================
'
'  Cambios v7.9.2:
'    - Abrir un fichero ya cargado en memoria (p. ej. una pieza de un
'      ensamblaje abierto) ya no falla con "The path is empty" cuando hay en
'      Inventor algun documento sin guardar. Ver AperturaInventorSegura.
'
'  Cambios v7.9.1:
'    - La busqueda se lanza sola al teclear (350 ms). Ya no depende de Intro,
'      que Inventor se traga en formularios no modales.
'    - Cabecera propia con botones Minimizar, Maximizar y Cerrar. Cerrar ya no
'      depende de la tecla Escape.
'    - Escape e Intro se cablean por cuatro vias distintas por si Inventor los
'      suelta: ProcessCmdKey, ProcessDialogKey, KeyDown del formulario e
'      IMessageFilter.
'    - Al relanzar la regla se activa la ventana ya abierta en vez de duplicarla.
'    - Interfaz rehecha en una sola pasada, con acento ambar en las acciones
'      principales y la paleta oscura de siempre.
'
'  Modos de indexado:
'    - Rapido: solo nombre (no necesita Inventor)
'    - Relaciones: proceso aparte en segundo plano que lee los ensamblajes
'
' =====================================================================

Sub Main()
    Try
        If BuscadorFicherosForm.Instancia IsNot Nothing AndAlso _
                Not BuscadorFicherosForm.Instancia.IsDisposed Then
            BuscadorFicherosForm.Instancia.Activate()
            Return
        End If
    Catch
    End Try

    Dim frm As New BuscadorFicherosForm(ThisApplication)
    BuscadorFicherosForm.Instancia = frm
    Try
        frm.Show(New VentanaInventor(New System.IntPtr( _
            System.Convert.ToInt64(ThisApplication.MainFrameHWND))))
    Catch
        frm.Show()
    End Try
    Try
        frm.Activate()
    Catch
    End Try
End Sub


' Envuelve el HWND de Inventor para poder mostrar el formulario como ventana
' hija suya. Sin esto la ventana se queda por detras y pierde el foco.
Public Class VentanaInventor
    Implements System.Windows.Forms.IWin32Window

    Private _identificador As System.IntPtr

    Public Sub New(identificador As System.IntPtr)
        _identificador = identificador
    End Sub

    Public ReadOnly Property Handle As System.IntPtr _
            Implements System.Windows.Forms.IWin32Window.Handle
        Get
            Return _identificador
        End Get
    End Property
End Class


Public Class BuscadorFicherosForm
    Inherits System.Windows.Forms.Form
    Implements System.Windows.Forms.IMessageFilter

    Public Shared Instancia As BuscadorFicherosForm

    Private Const RUTA_DEFECTO As String = "P:\"
    Private Const RUTA_RED As String = "\\192.168.10.217\DISEÑO"
    Private Const RUTA_INDICES As String = "P:\000 MARIANADAS\INDEX"
    Private Const MAX_RESULTADOS As Integer = 2000
    Private Const RETARDO_BUSQUEDA As Integer = 350
    Private Const MINIMO_BUSQUEDA As Integer = 2

    ' Arrastre y redimension de la ventana sin bordes.
    Private Declare Function ReleaseCapture Lib "user32.dll" () As Integer
    Private Declare Function SendMessage Lib "user32.dll" Alias "SendMessageA" ( _
        hWnd As System.IntPtr, mensaje As Integer, wParam As Integer, lParam As Integer) As Integer

    Private Const CODIGO_RELACIONES As String = _
        "JABFAHIAcgBvAHIAQQBjAHQAaQBvAG4AUAByAGUAZgBlAHIAZQBuAGMAZQAgAD0AIAAnAFMAdABvAHAAJwAKACQAYQByAGMAaABpAHYAbwBJAG4AZABpAGMAZQAgAD0AIAAkAGUAbgB2ADoAQgBVAFMAQwBBAEQATwBSAF8AQQBSAEMASABJAFYATwBfAEkATgBEAEkAQwBFAAoAJABhAHIAYwBoAGkAdgBvAFAAcgBvAGcAcgBlAHMAbwAgAD0AIAAkAGUAbgB2ADoAQgBVAFMAQwBBAEQATwBSAF8AQQBSAEMASABJAFYATwBfAFAAUgBPAEcAUgBFAFMATwAKACQAYQByAGMAaABpAHYAbwBDAGEAbgBjAGUAbABhAHIAIAA9ACAAJABlAG4AdgA6AEIAVQBTAEMAQQBEAE8AUgBfAEEAUgBDAEgASQBWAE8AXwBDAEEATgBDAEUATABBAFIACgAkAGEAcgBjAGgAaQB2AG8ARQByAHIAbwByACAAPQAgACQAZQBuAHYAOgBCAFUAUwBDAEEARABPAFIAXwBBAFIAQwBIAEkAVgBPAF8ARQBSAFIATwBSAAoAJABhAHAAcAAgAD0AIAAkAG4AdQBsAGwACgAkAHQAZQBtAHAAbwByAGEAbAAgAD0AIAAkAG4AdQBsAGwACgAkAHAAcgBvAGMAZQBzAGEAZABv" & _
        "AHMAIAA9ACAAMAAKACQAYQB2AGkAcwBvAHMAIAA9ACAAMAAKACQAYwBvAGQAaQBnAG8AUwBhAGwAaQBkAGEAIAA9ACAAMAAKAAoAZgB1AG4AYwB0AGkAbwBuACAAQgA2ADQAKABbAHMAdAByAGkAbgBnAF0AJAB0AGUAeAB0AG8AKQAgAHsACgAgACAAIAAgAFsAQwBvAG4AdgBlAHIAdABdADoAOgBUAG8AQgBhAHMAZQA2ADQAUwB0AHIAaQBuAGcAKABbAFQAZQB4AHQALgBFAG4AYwBvAGQAaQBuAGcAXQA6ADoAVQBUAEYAOAAuAEcAZQB0AEIAeQB0AGUAcwAoACQAdABlAHgAdABvACkAKQAKAH0ACgAKAGYAdQBuAGMAdABpAG8AbgAgAEYAcgBvAG0ALQBCADYANAAoAFsAcwB0AHIAaQBuAGcAXQAkAHQAZQB4AHQAbwApACAAewAKACAAIAAgACAAWwBUAGUAeAB0AC4ARQBuAGMAbwBkAGkAbgBnAF0AOgA6AFUAVABGADgALgBHAGUAdABTAHQAcgBpAG4AZwAoAFsAQwBvAG4AdgBlAHIAdABdADoAOgBGAHIAbwBtAEIAYQBzAGUANgA0AFMAdAByAGkAbgBnACgAJAB0AGUAeAB0AG8AKQApAAoAfQAKAAoAZgB1AG4AYwB0AGkAbwBuACAA" & _
        "QwBhAG4AYwBlAGwAYQBjAGkAbwBuAC0AUwBvAGwAaQBjAGkAdABhAGQAYQAgAHsACgAgACAAIAAgACQAYQByAGMAaABpAHYAbwBDAGEAbgBjAGUAbABhAHIAIAAtAGEAbgBkACAAWwBJAE8ALgBGAGkAbABlAF0AOgA6AEUAeABpAHMAdABzACgAJABhAHIAYwBoAGkAdgBvAEMAYQBuAGMAZQBsAGEAcgApAAoAfQAKAAoAZgB1AG4AYwB0AGkAbwBuACAARwB1AGEAcgBkAGEAcgAtAFAAcgBvAGcAcgBlAHMAbwAoAFsAaQBuAHQAXQAkAGgAZQBjAGgAbwBzACwAIABbAGkAbgB0AF0AJAB0AG8AdABhAGwALAAgAFsAaQBuAHQAXQAkAGMAYQBtAGIAaQBhAGQAbwBzACwAIABbAGkAbgB0AF0AJAB0AG8AdABhAGwAQwBhAG0AYgBpAG8AcwApACAAewAKACAAIAAgACAAaQBmACAAKAAtAG4AbwB0ACAAJABhAHIAYwBoAGkAdgBvAFAAcgBvAGcAcgBlAHMAbwApACAAewAgAHIAZQB0AHUAcgBuACAAfQAKACAAIAAgACAAJABjAG8AbgB0AGUAbgBpAGQAbwAgAD0AIAAiACQAaABlAGMAaABvAHMAfAAkAHQAbwB0AGEAbAB8ACQAYwBhAG0AYgBp" & _
        "AGEAZABvAHMAfAAkAHQAbwB0AGEAbABDAGEAbQBiAGkAbwBzACIACgAgACAAIAAgAGYAbwByACAAKAAkAGkAbgB0AGUAbgB0AG8AIAA9ACAAMAA7ACAAJABpAG4AdABlAG4AdABvACAALQBsAHQAIAAxADAAOwAgACQAaQBuAHQAZQBuAHQAbwArACsAKQAgAHsACgAgACAAIAAgACAAIAAgACAAdAByAHkAIAB7AAoAIAAgACAAIAAgACAAIAAgACAAIAAgACAAWwBJAE8ALgBGAGkAbABlAF0AOgA6AFcAcgBpAHQAZQBBAGwAbABUAGUAeAB0ACgAJABhAHIAYwBoAGkAdgBvAFAAcgBvAGcAcgBlAHMAbwAsACAAJABjAG8AbgB0AGUAbgBpAGQAbwApAAoAIAAgACAAIAAgACAAIAAgACAAIAAgACAAcgBlAHQAdQByAG4ACgAgACAAIAAgACAAIAAgACAAfQAgAGMAYQB0AGMAaAAgAFsASQBPAC4ASQBPAEUAeABjAGUAcAB0AGkAbwBuAF0AIAB7AAoAIAAgACAAIAAgACAAIAAgACAAIAAgACAAUwB0AGEAcgB0AC0AUwBsAGUAZQBwACAALQBNAGkAbABsAGkAcwBlAGMAbwBuAGQAcwAgADIANQAKACAAIAAgACAAIAAgACAAIAB9ACAAYwBhAHQA" & _
        "YwBoACAAWwBVAG4AYQB1AHQAaABvAHIAaQB6AGUAZABBAGMAYwBlAHMAcwBFAHgAYwBlAHAAdABpAG8AbgBdACAAewAKACAAIAAgACAAIAAgACAAIAAgACAAIAAgAFMAdABhAHIAdAAtAFMAbABlAGUAcAAgAC0ATQBpAGwAbABpAHMAZQBjAG8AbgBkAHMAIAAyADUACgAgACAAIAAgACAAIAAgACAAfQAKACAAIAAgACAAfQAKACAAIAAgACAAIwAgAEUAbAAgAHAAcgBvAGcAcgBlAHMAbwAgAGUAcwAgAGkAbgBmAG8AcgBtAGEAdABpAHYAbwA6ACAAdQBuACAAYgBsAG8AcQB1AGUAbwAgAG0AbwBtAGUAbgB0AGEAbgBlAG8AIABuAHUAbgBjAGEAIABkAGUAYgBlACAAZABlAHQAZQBuAGUAcgAKACAAIAAgACAAIwAgAGwAYQAgAGcAZQBuAGUAcgBhAGMAaQBvAG4AIABkAGUAbAAgAGkAbgBkAGkAYwBlACAAZABlACAAcgBlAGwAYQBjAGkAbwBuAGUAcwAuAAoAfQAKAAoAZgB1AG4AYwB0AGkAbwBuACAAUgBlAGUAbQBwAGwAYQB6AGEAcgAtAFMAZQBnAHUAcgBvACgAWwBzAHQAcgBpAG4AZwBdACQAbwByAGkAZwBlAG4ALAAgAFsAcwB0" & _
        "AHIAaQBuAGcAXQAkAGQAZQBzAHQAaQBuAG8AKQAgAHsACgAgACAAIAAgAGkAZgAgACgALQBuAG8AdAAgAFsASQBPAC4ARgBpAGwAZQBdADoAOgBFAHgAaQBzAHQAcwAoACQAZABlAHMAdABpAG4AbwApACkAIAB7AAoAIAAgACAAIAAgACAAIAAgAFsASQBPAC4ARgBpAGwAZQBdADoAOgBNAG8AdgBlACgAJABvAHIAaQBnAGUAbgAsACAAJABkAGUAcwB0AGkAbgBvACkACgAgACAAIAAgACAAIAAgACAAcgBlAHQAdQByAG4ACgAgACAAIAAgAH0ACgAgACAAIAAgAHQAcgB5ACAAewAKACAAIAAgACAAIAAgACAAIABbAEkATwAuAEYAaQBsAGUAXQA6ADoAUgBlAHAAbABhAGMAZQAoACQAbwByAGkAZwBlAG4ALAAgACQAZABlAHMAdABpAG4AbwAsACAAJABuAHUAbABsACkACgAgACAAIAAgAH0AIABjAGEAdABjAGgAIAB7AAoAIAAgACAAIAAgACAAIAAgACQAcgBlAHMAcABhAGwAZABvACAAPQAgACIAJABkAGUAcwB0AGkAbgBvAC4AJAAoAFsARwB1AGkAZABdADoAOgBOAGUAdwBHAHUAaQBkACgAKQAuAFQAbwBTAHQAcgBpAG4AZwAoACcA" & _
        "TgAnACkAKQAuAGIAYQBrACIACgAgACAAIAAgACAAIAAgACAAWwBJAE8ALgBGAGkAbABlAF0AOgA6AE0AbwB2AGUAKAAkAGQAZQBzAHQAaQBuAG8ALAAgACQAcgBlAHMAcABhAGwAZABvACkACgAgACAAIAAgACAAIAAgACAAdAByAHkAIAB7AAoAIAAgACAAIAAgACAAIAAgACAAIAAgACAAWwBJAE8ALgBGAGkAbABlAF0AOgA6AE0AbwB2AGUAKAAkAG8AcgBpAGcAZQBuACwAIAAkAGQAZQBzAHQAaQBuAG8AKQAKACAAIAAgACAAIAAgACAAIAAgACAAIAAgAFsASQBPAC4ARgBpAGwAZQBdADoAOgBEAGUAbABlAHQAZQAoACQAcgBlAHMAcABhAGwAZABvACkACgAgACAAIAAgACAAIAAgACAAfQAgAGMAYQB0AGMAaAAgAHsACgAgACAAIAAgACAAIAAgACAAIAAgACAAIABpAGYAIAAoAFsASQBPAC4ARgBpAGwAZQBdADoAOgBFAHgAaQBzAHQAcwAoACQAZABlAHMAdABpAG4AbwApACkAIAB7ACAAWwBJAE8ALgBGAGkAbABlAF0AOgA6AEQAZQBsAGUAdABlACgAJABkAGUAcwB0AGkAbgBvACkAIAB9AAoAIAAgACAAIAAgACAAIAAgACAAIAAg" & _
        "ACAAaQBmACAAKABbAEkATwAuAEYAaQBsAGUAXQA6ADoARQB4AGkAcwB0AHMAKAAkAHIAZQBzAHAAYQBsAGQAbwApACkAIAB7ACAAWwBJAE8ALgBGAGkAbABlAF0AOgA6AE0AbwB2AGUAKAAkAHIAZQBzAHAAYQBsAGQAbwAsACAAJABkAGUAcwB0AGkAbgBvACkAIAB9AAoAIAAgACAAIAAgACAAIAAgACAAIAAgACAAdABoAHIAbwB3AAoAIAAgACAAIAAgACAAIAAgAH0ACgAgACAAIAAgAH0ACgB9AAoACgB0AHIAeQAgAHsACgAgACAAIAAgAGkAZgAgACgAWwBzAHQAcgBpAG4AZwBdADoAOgBJAHMATgB1AGwAbABPAHIAVwBoAGkAdABlAFMAcABhAGMAZQAoACQAYQByAGMAaABpAHYAbwBJAG4AZABpAGMAZQApACAALQBvAHIAIAAtAG4AbwB0ACAAWwBJAE8ALgBGAGkAbABlAF0AOgA6AEUAeABpAHMAdABzACgAJABhAHIAYwBoAGkAdgBvAEkAbgBkAGkAYwBlACkAKQAgAHsACgAgACAAIAAgACAAIAAgACAAdABoAHIAbwB3ACAAIgBOAG8AIABlAHgAaQBzAHQAZQAgAGUAbAAgAO0AbgBkAGkAYwBlACAAcwBlAGwAZQBjAGMAaQBvAG4A" & _
        "YQBkAG8AOgAgACQAYQByAGMAaABpAHYAbwBJAG4AZABpAGMAZQAiAAoAIAAgACAAIAB9AAoACgAgACAAIAAgACQAZQBuAHMAYQBtAGIAbABhAGoAZQBzACAAPQAgAFsAUwB5AHMAdABlAG0ALgBDAG8AbABsAGUAYwB0AGkAbwBuAHMALgBHAGUAbgBlAHIAaQBjAC4ATABpAHMAdABbAG8AYgBqAGUAYwB0AF0AXQA6ADoAbgBlAHcAKAApAAoAIAAgACAAIAAkAHYAaQBzAHQAbwBzACAAPQAgAFsAUwB5AHMAdABlAG0ALgBDAG8AbABsAGUAYwB0AGkAbwBuAHMALgBHAGUAbgBlAHIAaQBjAC4ASABhAHMAaABTAGUAdABbAHMAdAByAGkAbgBnAF0AXQA6ADoAbgBlAHcAKABbAFMAdAByAGkAbgBnAEMAbwBtAHAAYQByAGUAcgBdADoAOgBPAHIAZABpAG4AYQBsAEkAZwBuAG8AcgBlAEMAYQBzAGUAKQAKACAAIAAgACAAZgBvAHIAZQBhAGMAaAAgACgAJABsAGkAbgBlAGEAIABpAG4AIABbAEkATwAuAEYAaQBsAGUAXQA6ADoAUgBlAGEAZABMAGkAbgBlAHMAKAAkAGEAcgBjAGgAaQB2AG8ASQBuAGQAaQBjAGUALAAgAFsAVABlAHgAdAAu" & _
        "AEUAbgBjAG8AZABpAG4AZwBdADoAOgBVAFQARgA4ACkAKQAgAHsACgAgACAAIAAgACAAIAAgACAAaQBmACAAKABDAGEAbgBjAGUAbABhAGMAaQBvAG4ALQBTAG8AbABpAGMAaQB0AGEAZABhACkAIAB7ACAAdABoAHIAbwB3ACAAWwBPAHAAZQByAGEAdABpAG8AbgBDAGEAbgBjAGUAbABlAGQARQB4AGMAZQBwAHQAaQBvAG4AXQA6ADoAbgBlAHcAKAApACAAfQAKACAAIAAgACAAIAAgACAAIABpAGYAIAAoAFsAcwB0AHIAaQBuAGcAXQA6ADoASQBzAE4AdQBsAGwATwByAFcAaABpAHQAZQBTAHAAYQBjAGUAKAAkAGwAaQBuAGUAYQApACAALQBvAHIAIAAkAGwAaQBuAGUAYQAuAFMAdABhAHIAdABzAFcAaQB0AGgAKAAnACMAJwApACkAIAB7ACAAYwBvAG4AdABpAG4AdQBlACAAfQAKACAAIAAgACAAIAAgACAAIAAkAHIAdQB0AGEAIAA9ACAAJABsAGkAbgBlAGEALgBTAHAAbABpAHQAKABbAGMAaABhAHIAXQA5ACkAWwAwAF0ALgBUAHIAaQBtACgAKQAKACAAIAAgACAAIAAgACAAIABpAGYAIAAoAFsASQBPAC4AUABhAHQAaABdADoA" & _
        "OgBHAGUAdABFAHgAdABlAG4AcwBpAG8AbgAoACQAcgB1AHQAYQApAC4AVABvAEwAbwB3AGUAcgBJAG4AdgBhAHIAaQBhAG4AdAAoACkAIAAtAG4AZQAgACcALgBpAGEAbQAnACAALQBvAHIAIAAtAG4AbwB0ACAAJAB2AGkAcwB0AG8AcwAuAEEAZABkACgAJAByAHUAdABhACkAKQAgAHsAIABjAG8AbgB0AGkAbgB1AGUAIAB9AAoAIAAgACAAIAAgACAAIAAgAGkAZgAgACgALQBuAG8AdAAgAFsASQBPAC4ARgBpAGwAZQBdADoAOgBFAHgAaQBzAHQAcwAoACQAcgB1AHQAYQApACkAIAB7ACAAJABhAHYAaQBzAG8AcwArACsAOwAgAGMAbwBuAHQAaQBuAHUAZQAgAH0ACgAgACAAIAAgACAAIAAgACAAJAB0AGkAYwBrAHMAIAA9ACAAWwBJAE8ALgBGAGkAbABlAF0AOgA6AEcAZQB0AEwAYQBzAHQAVwByAGkAdABlAFQAaQBtAGUAVQB0AGMAKAAkAHIAdQB0AGEAKQAuAFQAaQBjAGsAcwAKACAAIAAgACAAIAAgACAAIAAkAGUAbgBzAGEAbQBiAGwAYQBqAGUAcwAuAEEAZABkACgAWwBwAHMAYwB1AHMAdABvAG0AbwBiAGoAZQBjAHQAXQBA" & _
        "AHsAIABSAHUAdABhACAAPQAgACQAcgB1AHQAYQA7ACAAVABpAGMAawBzACAAPQAgACQAdABpAGMAawBzACAAfQApAAoAIAAgACAAIAB9AAoACgAgACAAIAAgACQAcwBhAGwAaQBkAGEAIAA9ACAAIgAkAGEAcgBjAGgAaQB2AG8ASQBuAGQAaQBjAGUALgB1AHMAbwBzACIACgAgACAAIAAgACQAYQBuAHQAZQByAGkAbwByAGUAcwAgAD0AIABAAHsAfQAKACAAIAAgACAAaQBmACAAKABbAEkATwAuAEYAaQBsAGUAXQA6ADoARQB4AGkAcwB0AHMAKAAkAHMAYQBsAGkAZABhACkAKQAgAHsACgAgACAAIAAgACAAIAAgACAAJABwAGEAZAByAGUAQQBjAHQAdQBhAGwAIAA9ACAAJABuAHUAbABsAAoAIAAgACAAIAAgACAAIAAgACQAYgBsAG8AcQB1AGUAQQBjAHQAdQBhAGwAIAA9ACAAJABuAHUAbABsAAoAIAAgACAAIAAgACAAIAAgACQAbABpAG4AZQBhAHMAVgBpAHMAdABhAHMAIAA9ACAAJABuAHUAbABsAAoAIAAgACAAIAAgACAAIAAgAGYAbwByAGUAYQBjAGgAIAAoACQAbABpAG4AZQBhACAAaQBuACAAWwBJAE8ALgBGAGkAbABlAF0A" & _
        "OgA6AFIAZQBhAGQATABpAG4AZQBzACgAJABzAGEAbABpAGQAYQAsACAAWwBUAGUAeAB0AC4ARQBuAGMAbwBkAGkAbgBnAF0AOgA6AFUAVABGADgAKQApACAAewAKACAAIAAgACAAIAAgACAAIAAgACAAIAAgAGkAZgAgACgAJABsAGkAbgBlAGEALgBTAHQAYQByAHQAcwBXAGkAdABoACgAIgBBAGAAdAAiACkAKQAgAHsACgAgACAAIAAgACAAIAAgACAAIAAgACAAIAAgACAAIAAgACQAcABhAHIAdABlAHMAIAA9ACAAJABsAGkAbgBlAGEALgBTAHAAbABpAHQAKABbAGMAaABhAHIAXQA5ACkACgAgACAAIAAgACAAIAAgACAAIAAgACAAIAAgACAAIAAgACQAcABhAGQAcgBlAEEAYwB0AHUAYQBsACAAPQAgACQAbgB1AGwAbAAKACAAIAAgACAAIAAgACAAIAAgACAAIAAgACAAIAAgACAAaQBmACAAKAAkAHAAYQByAHQAZQBzAC4ATABlAG4AZwB0AGgAIAAtAGcAZQAgADMAKQAgAHsACgAgACAAIAAgACAAIAAgACAAIAAgACAAIAAgACAAIAAgACAAIAAgACAAdAByAHkAIAB7AAoAIAAgACAAIAAgACAAIAAgACAAIAAgACAAIAAgACAAIAAg" & _
        "ACAAIAAgACAAIAAgACAAJAByAHUAdABhAEEAbgB0AGUAcgBpAG8AcgAgAD0AIABGAHIAbwBtAC0AQgA2ADQAIAAkAHAAYQByAHQAZQBzAFsAMQBdAAoAIAAgACAAIAAgACAAIAAgACAAIAAgACAAIAAgACAAIAAgACAAIAAgACAAIAAgACAAJAB0AGkAYwBrAHMAQQBuAHQAZQByAGkAbwByACAAPQAgADAATAAKACAAIAAgACAAIAAgACAAIAAgACAAIAAgACAAIAAgACAAIAAgACAAIAAgACAAIAAgAGkAZgAgACgAWwBsAG8AbgBnAF0AOgA6AFQAcgB5AFAAYQByAHMAZQAoACQAcABhAHIAdABlAHMAWwAyAF0ALAAgAFsAcgBlAGYAXQAkAHQAaQBjAGsAcwBBAG4AdABlAHIAaQBvAHIAKQApACAAewAKACAAIAAgACAAIAAgACAAIAAgACAAIAAgACAAIAAgACAAIAAgACAAIAAgACAAIAAgACAAIAAgACAAJABiAGwAbwBxAHUAZQBBAGMAdAB1AGEAbAAgAD0AIABbAFMAeQBzAHQAZQBtAC4AQwBvAGwAbABlAGMAdABpAG8AbgBzAC4ARwBlAG4AZQByAGkAYwAuAEwAaQBzAHQAWwBzAHQAcgBpAG4AZwBdAF0AOgA6AG4AZQB3ACgAKQAKACAA" & _
        "IAAgACAAIAAgACAAIAAgACAAIAAgACAAIAAgACAAIAAgACAAIAAgACAAIAAgACAAIAAgACAAJABsAGkAbgBlAGEAcwBWAGkAcwB0AGEAcwAgAD0AIABbAFMAeQBzAHQAZQBtAC4AQwBvAGwAbABlAGMAdABpAG8AbgBzAC4ARwBlAG4AZQByAGkAYwAuAEgAYQBzAGgAUwBlAHQAWwBzAHQAcgBpAG4AZwBdAF0AOgA6AG4AZQB3ACgAWwBTAHQAcgBpAG4AZwBDAG8AbQBwAGEAcgBlAHIAXQA6ADoATwByAGQAaQBuAGEAbAApAAoAIAAgACAAIAAgACAAIAAgACAAIAAgACAAIAAgACAAIAAgACAAIAAgACAAIAAgACAAIAAgACAAIAAkAGIAbABvAHEAdQBlAEEAYwB0AHUAYQBsAC4AQQBkAGQAKAAkAGwAaQBuAGUAYQApAAoAIAAgACAAIAAgACAAIAAgACAAIAAgACAAIAAgACAAIAAgACAAIAAgACAAIAAgACAAIAAgACAAIABbAHYAbwBpAGQAXQAkAGwAaQBuAGUAYQBzAFYAaQBzAHQAYQBzAC4AQQBkAGQAKAAkAGwAaQBuAGUAYQApAAoAIAAgACAAIAAgACAAIAAgACAAIAAgACAAIAAgACAAIAAgACAAIAAgACAAIAAgACAAIAAgACAAIAAk" & _
        "AGEAbgB0AGUAcgBpAG8AcgBlAHMAWwAkAHIAdQB0AGEAQQBuAHQAZQByAGkAbwByAF0AIAA9ACAAWwBwAHMAYwB1AHMAdABvAG0AbwBiAGoAZQBjAHQAXQBAAHsAIABUAGkAYwBrAHMAIAA9ACAAJAB0AGkAYwBrAHMAQQBuAHQAZQByAGkAbwByADsAIABMAGkAbgBlAGEAcwAgAD0AIAAkAGIAbABvAHEAdQBlAEEAYwB0AHUAYQBsACAAfQAKACAAIAAgACAAIAAgACAAIAAgACAAIAAgACAAIAAgACAAIAAgACAAIAAgACAAIAAgACAAIAAgACAAJABwAGEAZAByAGUAQQBjAHQAdQBhAGwAIAA9ACAAJAByAHUAdABhAEEAbgB0AGUAcgBpAG8AcgAKACAAIAAgACAAIAAgACAAIAAgACAAIAAgACAAIAAgACAAIAAgACAAIAAgACAAIAAgAH0ACgAgACAAIAAgACAAIAAgACAAIAAgACAAIAAgACAAIAAgACAAIAAgACAAfQAgAGMAYQB0AGMAaAAgAHsACgAgACAAIAAgACAAIAAgACAAIAAgACAAIAAgACAAIAAgACAAIAAgACAAIAAgACAAIAAkAHAAYQBkAHIAZQBBAGMAdAB1AGEAbAAgAD0AIAAkAG4AdQBsAGwACgAgACAAIAAgACAAIAAgACAA" & _
        "IAAgACAAIAAgACAAIAAgACAAIAAgACAAfQAKACAAIAAgACAAIAAgACAAIAAgACAAIAAgACAAIAAgACAAfQAKACAAIAAgACAAIAAgACAAIAAgACAAIAAgAH0AIABlAGwAcwBlAGkAZgAgACgAJABuAHUAbABsACAALQBuAGUAIAAkAHAAYQBkAHIAZQBBAGMAdAB1AGEAbAAgAC0AYQBuAGQAIAAoACQAbABpAG4AZQBhAC4AUwB0AGEAcgB0AHMAVwBpAHQAaAAoACIAUgBgAHQAIgApACAALQBvAHIAIAAkAGwAaQBuAGUAYQAuAFMAdABhAHIAdABzAFcAaQB0AGgAKAAiAEUAYAB0ACIAKQApACkAIAB7AAoAIAAgACAAIAAgACAAIAAgACAAIAAgACAAIAAgACAAIABpAGYAIAAoACQAbABpAG4AZQBhAHMAVgBpAHMAdABhAHMALgBBAGQAZAAoACQAbABpAG4AZQBhACkAKQAgAHsAIAAkAGIAbABvAHEAdQBlAEEAYwB0AHUAYQBsAC4AQQBkAGQAKAAkAGwAaQBuAGUAYQApACAAfQAKACAAIAAgACAAIAAgACAAIAAgACAAIAAgAH0ACgAgACAAIAAgACAAIAAgACAAfQAKACAAIAAgACAAfQAKAAoAIAAgACAAIAAkAHQAbwB0AGEAbABDAGEAbQBi" & _
        "AGkAbwBzACAAPQAgADAACgAgACAAIAAgAGYAbwByAGUAYQBjAGgAIAAoACQAZQBuAHQAcgBhAGQAYQAgAGkAbgAgACQAZQBuAHMAYQBtAGIAbABhAGoAZQBzACkAIAB7AAoAIAAgACAAIAAgACAAIAAgACQAYQBuAHQAZQByAGkAbwByACAAPQAgACQAYQBuAHQAZQByAGkAbwByAGUAcwBbACQAZQBuAHQAcgBhAGQAYQAuAFIAdQB0AGEAXQAKACAAIAAgACAAIAAgACAAIABpAGYAIAAoACQAbgB1AGwAbAAgAC0AZQBxACAAJABhAG4AdABlAHIAaQBvAHIAIAAtAG8AcgAgACQAYQBuAHQAZQByAGkAbwByAC4AVABpAGMAawBzACAALQBuAGUAIAAkAGUAbgB0AHIAYQBkAGEALgBUAGkAYwBrAHMAKQAgAHsAIAAkAHQAbwB0AGEAbABDAGEAbQBiAGkAbwBzACsAKwAgAH0ACgAgACAAIAAgAH0ACgAKACAAIAAgACAARwB1AGEAcgBkAGEAcgAtAFAAcgBvAGcAcgBlAHMAbwAgADAAIAAkAGUAbgBzAGEAbQBiAGwAYQBqAGUAcwAuAEMAbwB1AG4AdAAgADAAIAAkAHQAbwB0AGEAbABDAGEAbQBiAGkAbwBzAAoAIAAgACAAIABpAGYAIAAoACQA" & _
        "dABvAHQAYQBsAEMAYQBtAGIAaQBvAHMAIAAtAGcAdAAgADAAKQAgAHsACgAgACAAIAAgACAAIAAgACAAJABhAHAAcAAgAD0AIABOAGUAdwAtAE8AYgBqAGUAYwB0ACAALQBDAG8AbQBPAGIAagBlAGMAdAAgAEkAbgB2AGUAbgB0AG8AcgAuAEEAcABwAGwAaQBjAGEAdABpAG8AbgAKACAAIAAgACAAIAAgACAAIAAkAGEAcABwAC4AVgBpAHMAaQBiAGwAZQAgAD0AIAAkAGYAYQBsAHMAZQAKACAAIAAgACAAIAAgACAAIAAkAGEAcABwAC4AUwBpAGwAZQBuAHQATwBwAGUAcgBhAHQAaQBvAG4AIAA9ACAAJAB0AHIAdQBlAAoAIAAgACAAIAB9AAoACgAgACAAIAAgACQAdABlAG0AcABvAHIAYQBsACAAPQAgACIAJABzAGEAbABpAGQAYQAuACQAKABbAEcAdQBpAGQAXQA6ADoATgBlAHcARwB1AGkAZAAoACkALgBUAG8AUwB0AHIAaQBuAGcAKAAnAE4AJwApACkALgB0AG0AcAAiAAoAIAAgACAAIAAkAHcAcgBpAHQAZQByACAAPQAgAE4AZQB3AC0ATwBiAGoAZQBjAHQAIABJAE8ALgBTAHQAcgBlAGEAbQBXAHIAaQB0AGUAcgAoACQAdABl" & _
        "AG0AcABvAHIAYQBsACwAIAAkAGYAYQBsAHMAZQAsACAAKABOAGUAdwAtAE8AYgBqAGUAYwB0ACAAVABlAHgAdAAuAFUAVABGADgARQBuAGMAbwBkAGkAbgBnACgAJABmAGEAbABzAGUAKQApACkACgAgACAAIAAgAHQAcgB5ACAAewAKACAAIAAgACAAIAAgACAAIAAkAHcAcgBpAHQAZQByAC4AVwByAGkAdABlAEwAaQBuAGUAKAAiACMAVQBTAE8AUwAyAGAAdAAkACgAWwBEAGEAdABlAFQAaQBtAGUAXQA6ADoATgBvAHcALgBUAG8AUwB0AHIAaQBuAGcAKAAnAHkAeQB5AHkALQBNAE0ALQBkAGQAIABIAEgAOgBtAG0AOgBzAHMAJwApACkAIgApAAoAIAAgACAAIAAgACAAIAAgACQAYwBhAG0AYgBpAGEAZABvAHMAIAA9ACAAMAAKACAAIAAgACAAIAAgACAAIABmAG8AcgBlAGEAYwBoACAAKAAkAGUAbgB0AHIAYQBkAGEAIABpAG4AIAAkAGUAbgBzAGEAbQBiAGwAYQBqAGUAcwApACAAewAKACAAIAAgACAAIAAgACAAIAAgACAAIAAgAGkAZgAgACgAQwBhAG4AYwBlAGwAYQBjAGkAbwBuAC0AUwBvAGwAaQBjAGkAdABhAGQAYQApACAA" & _
        "ewAgAHQAaAByAG8AdwAgAFsATwBwAGUAcgBhAHQAaQBvAG4AQwBhAG4AYwBlAGwAZQBkAEUAeABjAGUAcAB0AGkAbwBuAF0AOgA6AG4AZQB3ACgAKQAgAH0ACgAgACAAIAAgACAAIAAgACAAIAAgACAAIAAkAGEAbgB0AGUAcgBpAG8AcgAgAD0AIAAkAGEAbgB0AGUAcgBpAG8AcgBlAHMAWwAkAGUAbgB0AHIAYQBkAGEALgBSAHUAdABhAF0ACgAgACAAIAAgACAAIAAgACAAIAAgACAAIABpAGYAIAAoACQAbgB1AGwAbAAgAC0AbgBlACAAJABhAG4AdABlAHIAaQBvAHIAIAAtAGEAbgBkACAAJABhAG4AdABlAHIAaQBvAHIALgBUAGkAYwBrAHMAIAAtAGUAcQAgACQAZQBuAHQAcgBhAGQAYQAuAFQAaQBjAGsAcwApACAAewAKACAAIAAgACAAIAAgACAAIAAgACAAIAAgACAAIAAgACAAZgBvAHIAZQBhAGMAaAAgACgAJABsAGkAbgBlAGEAQQBuAHQAZQByAGkAbwByACAAaQBuACAAJABhAG4AdABlAHIAaQBvAHIALgBMAGkAbgBlAGEAcwApACAAewAgACQAdwByAGkAdABlAHIALgBXAHIAaQB0AGUATABpAG4AZQAoACQAbABpAG4AZQBh" & _
        "AEEAbgB0AGUAcgBpAG8AcgApACAAfQAKACAAIAAgACAAIAAgACAAIAAgACAAIAAgAH0AIABlAGwAcwBlACAAewAKACAAIAAgACAAIAAgACAAIAAgACAAIAAgACAAIAAgACAAJAB3AHIAaQB0AGUAcgAuAFcAcgBpAHQAZQBMAGkAbgBlACgAIgBBAGAAdAAkACgAQgA2ADQAIAAkAGUAbgB0AHIAYQBkAGEALgBSAHUAdABhACkAYAB0ACQAKAAkAGUAbgB0AHIAYQBkAGEALgBUAGkAYwBrAHMAKQAiACkACgAgACAAIAAgACAAIAAgACAAIAAgACAAIAAgACAAIAAgACQAZABvAGMAIAA9ACAAJABuAHUAbABsAAoAIAAgACAAIAAgACAAIAAgACAAIAAgACAAIAAgACAAIAAkAGgAaQBqAG8AcwBWAGkAcwB0AG8AcwAgAD0AIABbAFMAeQBzAHQAZQBtAC4AQwBvAGwAbABlAGMAdABpAG8AbgBzAC4ARwBlAG4AZQByAGkAYwAuAEgAYQBzAGgAUwBlAHQAWwBzAHQAcgBpAG4AZwBdAF0AOgA6AG4AZQB3ACgAWwBTAHQAcgBpAG4AZwBDAG8AbQBwAGEAcgBlAHIAXQA6ADoATwByAGQAaQBuAGEAbABJAGcAbgBvAHIAZQBDAGEAcwBlACkACgAgACAA" & _
        "IAAgACAAIAAgACAAIAAgACAAIAAgACAAIAAgAHQAcgB5ACAAewAKACAAIAAgACAAIAAgACAAIAAgACAAIAAgACAAIAAgACAAIAAgACAAIAAkAGQAbwBjACAAPQAgACQAYQBwAHAALgBEAG8AYwB1AG0AZQBuAHQAcwAuAE8AcABlAG4AKAAkAGUAbgB0AHIAYQBkAGEALgBSAHUAdABhACwAIAAkAGYAYQBsAHMAZQApAAoAIAAgACAAIAAgACAAIAAgACAAIAAgACAAIAAgACAAIAAgACAAIAAgAGYAbwByAGUAYQBjAGgAIAAoACQAcgBlAGYAIABpAG4AIAAkAGQAbwBjAC4ARgBpAGwAZQAuAFIAZQBmAGUAcgBlAG4AYwBlAGQARgBpAGwAZQBEAGUAcwBjAHIAaQBwAHQAbwByAHMAKQAgAHsACgAgACAAIAAgACAAIAAgACAAIAAgACAAIAAgACAAIAAgACAAIAAgACAAIAAgACAAIAB0AHIAeQAgAHsACgAgACAAIAAgACAAIAAgACAAIAAgACAAIAAgACAAIAAgACAAIAAgACAAIAAgACAAIAAgACAAIAAgACQAaABpAGoAbwAgAD0AIABbAHMAdAByAGkAbgBnAF0AJAByAGUAZgAuAEYAdQBsAGwARgBpAGwAZQBOAGEAbQBlAAoAIAAgACAAIAAg" & _
        "ACAAIAAgACAAIAAgACAAIAAgACAAIAAgACAAIAAgACAAIAAgACAAIAAgACAAIAAkAGUAeAB0ACAAPQAgAFsASQBPAC4AUABhAHQAaABdADoAOgBHAGUAdABFAHgAdABlAG4AcwBpAG8AbgAoACQAaABpAGoAbwApAC4AVABvAEwAbwB3AGUAcgBJAG4AdgBhAHIAaQBhAG4AdAAoACkACgAgACAAIAAgACAAIAAgACAAIAAgACAAIAAgACAAIAAgACAAIAAgACAAIAAgACAAIAAgACAAIAAgAGkAZgAgACgAKAAkAGUAeAB0ACAALQBuAGUAIAAnAC4AaQBwAHQAJwAgAC0AYQBuAGQAIAAkAGUAeAB0ACAALQBuAGUAIAAnAC4AaQBhAG0AJwApACAALQBvAHIAIAAtAG4AbwB0ACAAJABoAGkAagBvAHMAVgBpAHMAdABvAHMALgBBAGQAZAAoACQAaABpAGoAbwApACkAIAB7ACAAYwBvAG4AdABpAG4AdQBlACAAfQAKACAAIAAgACAAIAAgACAAIAAgACAAIAAgACAAIAAgACAAIAAgACAAIAAgACAAIAAgACAAIAAgACAAaQBmACAAKAAkAHIAZQBmAC4AUgBlAGYAZQByAGUAbgBjAGUATQBpAHMAcwBpAG4AZwAgAC0AbwByACAAJAByAGUAZgAuAFIA" & _
        "ZQBmAGUAcgBlAG4AYwBlAEkAbgB0AGUAcgBuAGEAbABOAGEAbQBlAEQAaQBmAGYAZQByAGUAbgB0ACkAIAB7AAoAIAAgACAAIAAgACAAIAAgACAAIAAgACAAIAAgACAAIAAgACAAIAAgACAAIAAgACAAIAAgACAAIAAgACAAIAAgACQAYQB2AGkAcwBvAHMAKwArAAoAIAAgACAAIAAgACAAIAAgACAAIAAgACAAIAAgACAAIAAgACAAIAAgACAAIAAgACAAIAAgACAAIAAgACAAIAAgACQAdwByAGkAdABlAHIALgBXAHIAaQB0AGUATABpAG4AZQAoACIARQBgAHQAJAAoAEIANgA0ACAAKAAkAGUAbgB0AHIAYQBkAGEALgBSAHUAdABhACsAJwAgAC0APgAgACcAKwAkAGgAaQBqAG8AKwAnADoAIAByAGUAZgBlAHIAZQBuAGMAaQBhACAAbgBvACAAcgBlAHMAdQBlAGwAdABhACcAKQApACIAKQAKACAAIAAgACAAIAAgACAAIAAgACAAIAAgACAAIAAgACAAIAAgACAAIAAgACAAIAAgACAAIAAgACAAfQAgAGUAbABzAGUAIAB7AAoAIAAgACAAIAAgACAAIAAgACAAIAAgACAAIAAgACAAIAAgACAAIAAgACAAIAAgACAAIAAgACAAIAAgACAAIAAg" & _
        "ACQAdwByAGkAdABlAHIALgBXAHIAaQB0AGUATABpAG4AZQAoACIAUgBgAHQAJAAoAEIANgA0ACAAJABlAG4AdAByAGEAZABhAC4AUgB1AHQAYQApAGAAdAAkACgAQgA2ADQAIAAkAGgAaQBqAG8AKQAiACkACgAgACAAIAAgACAAIAAgACAAIAAgACAAIAAgACAAIAAgACAAIAAgACAAIAAgACAAIAAgACAAIAAgAH0ACgAgACAAIAAgACAAIAAgACAAIAAgACAAIAAgACAAIAAgACAAIAAgACAAIAAgACAAIAB9ACAAYwBhAHQAYwBoACAAewAgACQAYQB2AGkAcwBvAHMAKwArACAAfQAKACAAIAAgACAAIAAgACAAIAAgACAAIAAgACAAIAAgACAAIAAgACAAIAB9AAoAIAAgACAAIAAgACAAIAAgACAAIAAgACAAIAAgACAAIAB9ACAAYwBhAHQAYwBoACAAewAKACAAIAAgACAAIAAgACAAIAAgACAAIAAgACAAIAAgACAAIAAgACAAIAAkAGEAdgBpAHMAbwBzACsAKwAKACAAIAAgACAAIAAgACAAIAAgACAAIAAgACAAIAAgACAAIAAgACAAIAAkAHcAcgBpAHQAZQByAC4AVwByAGkAdABlAEwAaQBuAGUAKAAiAEUAYAB0ACQAKABCADYANAAgACgA" & _
        "JABlAG4AdAByAGEAZABhAC4AUgB1AHQAYQArACcAIAAtAD4AIAAnACsAJABfAC4ARQB4AGMAZQBwAHQAaQBvAG4ALgBNAGUAcwBzAGEAZwBlACkAKQAiACkACgAgACAAIAAgACAAIAAgACAAIAAgACAAIAAgACAAIAAgAH0AIABmAGkAbgBhAGwAbAB5ACAAewAKACAAIAAgACAAIAAgACAAIAAgACAAIAAgACAAIAAgACAAIAAgACAAIABpAGYAIAAoACQAbgB1AGwAbAAgAC0AbgBlACAAJABkAG8AYwApACAAewAgAHQAcgB5ACAAewAgACQAZABvAGMALgBDAGwAbwBzAGUAKAAkAHQAcgB1AGUAKQAgAH0AIABjAGEAdABjAGgAIAB7AH0AIAB9AAoAIAAgACAAIAAgACAAIAAgACAAIAAgACAAIAAgACAAIAAgACAAIAAgAGkAZgAgACgAJABuAHUAbABsACAALQBuAGUAIAAkAGQAbwBjACkAIAB7ACAAdAByAHkAIAB7ACAAWwBSAHUAbgB0AGkAbQBlAC4ASQBuAHQAZQByAG8AcABTAGUAcgB2AGkAYwBlAHMALgBNAGEAcgBzAGgAYQBsAF0AOgA6AEYAaQBuAGEAbABSAGUAbABlAGEAcwBlAEMAbwBtAE8AYgBqAGUAYwB0ACgAJABkAG8AYwAp" & _
        "ACAAfAAgAE8AdQB0AC0ATgB1AGwAbAAgAH0AIABjAGEAdABjAGgAIAB7AH0AIAB9AAoAIAAgACAAIAAgACAAIAAgACAAIAAgACAAIAAgACAAIAAgACAAIAAgACQAZABvAGMAIAA9ACAAJABuAHUAbABsAAoAIAAgACAAIAAgACAAIAAgACAAIAAgACAAIAAgACAAIAB9AAoAIAAgACAAIAAgACAAIAAgACAAIAAgACAAIAAgACAAIAAkAGMAYQBtAGIAaQBhAGQAbwBzACsAKwAKACAAIAAgACAAIAAgACAAIAAgACAAIAAgAH0ACgAgACAAIAAgACAAIAAgACAAIAAgACAAIAAkAHAAcgBvAGMAZQBzAGEAZABvAHMAKwArAAoAIAAgACAAIAAgACAAIAAgACAAIAAgACAARwB1AGEAcgBkAGEAcgAtAFAAcgBvAGcAcgBlAHMAbwAgACQAcAByAG8AYwBlAHMAYQBkAG8AcwAgACQAZQBuAHMAYQBtAGIAbABhAGoAZQBzAC4AQwBvAHUAbgB0ACAAJABjAGEAbQBiAGkAYQBkAG8AcwAgACQAdABvAHQAYQBsAEMAYQBtAGIAaQBvAHMACgAgACAAIAAgACAAIAAgACAAfQAKACAAIAAgACAAfQAgAGYAaQBuAGEAbABsAHkAIAB7AAoAIAAgACAAIAAgACAA" & _
        "IAAgACQAdwByAGkAdABlAHIALgBEAGkAcwBwAG8AcwBlACgAKQAKACAAIAAgACAAfQAKAAoAIAAgACAAIABpAGYAIAAoAEMAYQBuAGMAZQBsAGEAYwBpAG8AbgAtAFMAbwBsAGkAYwBpAHQAYQBkAGEAKQAgAHsAIAB0AGgAcgBvAHcAIABbAE8AcABlAHIAYQB0AGkAbwBuAEMAYQBuAGMAZQBsAGUAZABFAHgAYwBlAHAAdABpAG8AbgBdADoAOgBuAGUAdwAoACkAIAB9AAoAIAAgACAAIABSAGUAZQBtAHAAbABhAHoAYQByAC0AUwBlAGcAdQByAG8AIAAkAHQAZQBtAHAAbwByAGEAbAAgACQAcwBhAGwAaQBkAGEACgAgACAAIAAgACQAdABlAG0AcABvAHIAYQBsACAAPQAgACQAbgB1AGwAbAAKACAAIAAgACAARwB1AGEAcgBkAGEAcgAtAFAAcgBvAGcAcgBlAHMAbwAgACQAZQBuAHMAYQBtAGIAbABhAGoAZQBzAC4AQwBvAHUAbgB0ACAAJABlAG4AcwBhAG0AYgBsAGEAagBlAHMALgBDAG8AdQBuAHQAIAAkAHQAbwB0AGEAbABDAGEAbQBiAGkAbwBzACAAJAB0AG8AdABhAGwAQwBhAG0AYgBpAG8AcwAKAH0AIABjAGEAdABjAGgAIABb" & _
        "AE8AcABlAHIAYQB0AGkAbwBuAEMAYQBuAGMAZQBsAGUAZABFAHgAYwBlAHAAdABpAG8AbgBdACAAewAKACAAIAAgACAAJABjAG8AZABpAGcAbwBTAGEAbABpAGQAYQAgAD0AIAAyAAoAfQAgAGMAYQB0AGMAaAAgAHsACgAgACAAIAAgAFsAQwBvAG4AcwBvAGwAZQBdADoAOgBFAHIAcgBvAHIALgBXAHIAaQB0AGUATABpAG4AZQAoACQAXwAuAEUAeABjAGUAcAB0AGkAbwBuAC4ATQBlAHMAcwBhAGcAZQApAAoAIAAgACAAIABpAGYAIAAoACQAYQByAGMAaABpAHYAbwBFAHIAcgBvAHIAKQAgAHsACgAgACAAIAAgACAAIAAgACAAdAByAHkAIAB7ACAAWwBJAE8ALgBGAGkAbABlAF0AOgA6AFcAcgBpAHQAZQBBAGwAbABUAGUAeAB0ACgAJABhAHIAYwBoAGkAdgBvAEUAcgByAG8AcgAsACAAJABfAC4ARQB4AGMAZQBwAHQAaQBvAG4ALgBUAG8AUwB0AHIAaQBuAGcAKAApACwAIABbAFQAZQB4AHQALgBFAG4AYwBvAGQAaQBuAGcAXQA6ADoAVQBUAEYAOAApACAAfQAgAGMAYQB0AGMAaAAgAHsAfQAKACAAIAAgACAAfQAKACAAIAAgACAA" & _
        "JABjAG8AZABpAGcAbwBTAGEAbABpAGQAYQAgAD0AIAAxAAoAfQAgAGYAaQBuAGEAbABsAHkAIAB7AAoAIAAgACAAIABpAGYAIAAoACQAbgB1AGwAbAAgAC0AbgBlACAAJABhAHAAcAApACAAewAKACAAIAAgACAAIAAgACAAIAB0AHIAeQAgAHsAIAAkAGEAcABwAC4AUQB1AGkAdAAoACkAIAB9ACAAYwBhAHQAYwBoACAAewB9AAoAIAAgACAAIAAgACAAIAAgAHQAcgB5ACAAewAgAFsAUgB1AG4AdABpAG0AZQAuAEkAbgB0AGUAcgBvAHAAUwBlAHIAdgBpAGMAZQBzAC4ATQBhAHIAcwBoAGEAbABdADoAOgBSAGUAbABlAGEAcwBlAEMAbwBtAE8AYgBqAGUAYwB0ACgAJABhAHAAcAApACAAfAAgAE8AdQB0AC0ATgB1AGwAbAAgAH0AIABjAGEAdABjAGgAIAB7AH0ACgAgACAAIAAgAH0ACgAgACAAIAAgAGkAZgAgACgAJABuAHUAbABsACAALQBuAGUAIAAkAHQAZQBtAHAAbwByAGEAbAAgAC0AYQBuAGQAIABbAEkATwAuAEYAaQBsAGUAXQA6ADoARQB4AGkAcwB0AHMAKAAkAHQAZQBtAHAAbwByAGEAbAApACkAIAB7AAoAIAAgACAAIAAg" & _
        "ACAAIAAgAHQAcgB5ACAAewAgAFsASQBPAC4ARgBpAGwAZQBdADoAOgBEAGUAbABlAHQAZQAoACQAdABlAG0AcABvAHIAYQBsACkAIAB9ACAAYwBhAHQAYwBoACAAewB9AAoAIAAgACAAIAB9AAoAfQAKAAoAZQB4AGkAdAAgACQAYwBvAGQAaQBnAG8AUwBhAGwAaQBkAGEACgA="

    Private procesoRelaciones As System.Diagnostics.Process
    Private relojProcesoRelaciones As System.Windows.Forms.Timer
    Private relojOcultarProgreso As System.Windows.Forms.Timer
    Private carpetaRelacionesActiva As String = ""
    Private archivoProgresoRelaciones As String = ""
    Private archivoCancelarRelaciones As String = ""
    Private archivoErrorRelaciones As String = ""

    Private Function ProcesoRelacionesActivo() As Boolean
        Try
            Return procesoRelaciones IsNot Nothing AndAlso Not procesoRelaciones.HasExited
        Catch
            Return False
        End Try
    End Function

    Private Sub LanzarRelacionesEnSegundoInventor()
        If ProcesoRelacionesActivo() Then
            lblEstado.Text = "Las relaciones ya se estan actualizando. Puedes seguir trabajando."
            Return
        End If
        Try
            carpetaRelacionesActiva = CarpetaIndice()
            Dim archivoIndice As String = _archivoIndexadoEnCurso
            If archivoIndice = "" OrElse Not System.IO.File.Exists(archivoIndice) Then archivoIndice = ArchivoIndiceActual()
            If Not System.IO.File.Exists(archivoIndice) Then Throw New System.Exception("No existe el indice que se acaba de crear.")

            archivoProgresoRelaciones = System.IO.Path.Combine(System.IO.Path.GetTempPath(), "BuscadorRelaciones_" & System.Guid.NewGuid().ToString("N") & ".txt")
            archivoCancelarRelaciones = archivoProgresoRelaciones & ".cancelar"
            archivoErrorRelaciones = archivoProgresoRelaciones & ".error"
            Try
                If System.IO.File.Exists(archivoProgresoRelaciones) Then System.IO.File.Delete(archivoProgresoRelaciones)
                If System.IO.File.Exists(archivoCancelarRelaciones) Then System.IO.File.Delete(archivoCancelarRelaciones)
                If System.IO.File.Exists(archivoErrorRelaciones) Then System.IO.File.Delete(archivoErrorRelaciones)
            Catch
            End Try

            Dim inicio As New System.Diagnostics.ProcessStartInfo()
            inicio.FileName = System.IO.Path.Combine(System.Environment.GetFolderPath(System.Environment.SpecialFolder.Windows), "System32\WindowsPowerShell\v1.0\powershell.exe")
            inicio.Arguments = "-NoProfile -NonInteractive -STA -EncodedCommand " & CODIGO_RELACIONES
            inicio.UseShellExecute = False
            inicio.CreateNoWindow = True
            inicio.WindowStyle = System.Diagnostics.ProcessWindowStyle.Hidden
            inicio.EnvironmentVariables("BUSCADOR_ARCHIVO_INDICE") = archivoIndice
            inicio.EnvironmentVariables("BUSCADOR_ARCHIVO_PROGRESO") = archivoProgresoRelaciones
            inicio.EnvironmentVariables("BUSCADOR_ARCHIVO_CANCELAR") = archivoCancelarRelaciones
            inicio.EnvironmentVariables("BUSCADOR_ARCHIVO_ERROR") = archivoErrorRelaciones
            procesoRelaciones = System.Diagnostics.Process.Start(inicio)

            If relojProcesoRelaciones Is Nothing Then
                relojProcesoRelaciones = New System.Windows.Forms.Timer()
                relojProcesoRelaciones.Interval = 500
                AddHandler relojProcesoRelaciones.Tick, AddressOf ComprobarRelaciones
            End If
            relojProcesoRelaciones.Start()
            btnIndexar.Enabled = False : btnActualizar.Enabled = False
            btnBuscar.Enabled = True : btnCancelar.Enabled = True
            HabilitarAccionesResultados(False)
            barraProgreso.Style = System.Windows.Forms.ProgressBarStyle.Blocks
            barraProgreso.Minimum = 0 : barraProgreso.Maximum = 100 : barraProgreso.Value = 0
            barraProgreso.Visible = True
            lblPorcentaje.Text = "0 %" : lblPorcentaje.Visible = True
            lblEstado.Text = "Relaciones: 0 %. Revisando ensamblajes nuevos o modificados. Puedes seguir trabajando."
        Catch ex As System.Exception
            btnIndexar.Enabled = True : btnActualizar.Enabled = True
            btnBuscar.Enabled = True : btnCancelar.Enabled = False
            lblEstado.Text = "No se pudo iniciar la actualizacion de relaciones: " & ex.Message
            OcultarProgresoEnBreve()
        End Try
    End Sub

    Private Sub ComprobarRelaciones(sender As Object, E As System.EventArgs)
        If procesoRelaciones Is Nothing Then Return
        Try
            If System.IO.File.Exists(archivoProgresoRelaciones) Then
                Dim textoProgreso As String = LeerArchivoCompartido(archivoProgresoRelaciones)
                Dim p As String() = textoProgreso.Split("|"c)
                Dim hechos As Integer : Dim total As Integer
                Dim cambiados As Integer : Dim totalCambios As Integer
                If p.Length >= 2 AndAlso Integer.TryParse(p(0), hechos) AndAlso Integer.TryParse(p(1), total) Then
                    If p.Length >= 4 Then
                        Integer.TryParse(p(2), cambiados) : Integer.TryParse(p(3), totalCambios)
                    End If
                    Dim porcentaje As Integer = If(totalCambios > 0, System.Math.Min(100, CInt(System.Math.Floor(CDbl(cambiados) * 100.0 / CDbl(totalCambios)))), 100)
                    barraProgreso.Minimum = 0 : barraProgreso.Maximum = 100 : barraProgreso.Value = porcentaje
                    lblPorcentaje.Text = porcentaje.ToString() & " %" : lblPorcentaje.Visible = True
                    lblEstado.Text = "Relaciones: " & porcentaje.ToString() & " % (" & cambiados.ToString() & " de " & totalCambios.ToString() & " IAM nuevos o modificados). Puedes seguir trabajando."
                End If
            End If
        Catch
        End Try
        If ProcesoRelacionesActivo() Then Return

        relojProcesoRelaciones.Stop()
        Dim codigo As Integer = -1
        Try : codigo = procesoRelaciones.ExitCode : Catch : End Try
        Try : procesoRelaciones.Dispose() : Catch : End Try
        procesoRelaciones = Nothing
        btnIndexar.Enabled = True : btnActualizar.Enabled = True
        btnBuscar.Enabled = True : btnCancelar.Enabled = False
        HabilitarAccionesResultados(True)
        cancelar = False
        If codigo = 0 Then
            barraProgreso.Maximum = 100 : barraProgreso.Value = 100
            lblPorcentaje.Text = "100 %" : lblPorcentaje.Visible = True
            lblEstado.Text = "Relaciones actualizadas: 100 %."
            If panelUsos IsNot Nothing Then panelUsos.CambiarCarpeta(carpetaRelacionesActiva, True)
        ElseIf codigo = 2 Then
            lblEstado.Text = "Actualizacion de relaciones cancelada."
        Else
            Dim detalle As String = ""
            Try
                If System.IO.File.Exists(archivoErrorRelaciones) Then detalle = System.IO.File.ReadAllText(archivoErrorRelaciones).Trim()
            Catch
            End Try
            If detalle.Contains(vbCr) Then detalle = detalle.Substring(0, detalle.IndexOf(vbCr))
            If detalle.Contains(vbLf) Then detalle = detalle.Substring(0, detalle.IndexOf(vbLf))
            If detalle.Length > 220 Then detalle = detalle.Substring(0, 220) & "..."
            lblEstado.Text = If(detalle = "", "No se pudieron completar las relaciones.", "Error de relaciones: " & detalle)
        End If
        LimpiarArchivosTemporalesRelaciones()
        OcultarProgresoEnBreve()
    End Sub

    Private Function LeerArchivoCompartido(ruta As String) As String
        Using flujo As New System.IO.FileStream(ruta, System.IO.FileMode.Open, System.IO.FileAccess.Read, System.IO.FileShare.ReadWrite Or System.IO.FileShare.Delete)
            Using lector As New System.IO.StreamReader(flujo, System.Text.Encoding.UTF8)
                Return lector.ReadToEnd()
            End Using
        End Using
    End Function

    Private Sub SolicitarCancelacionRelaciones()
        If Not ProcesoRelacionesActivo() Then Return
        Try
            System.IO.File.WriteAllText(archivoCancelarRelaciones, "cancelar")
        Catch
        End Try
    End Sub

    Private Sub LimpiarArchivosTemporalesRelaciones()
        Try
            If archivoProgresoRelaciones <> "" AndAlso System.IO.File.Exists(archivoProgresoRelaciones) Then System.IO.File.Delete(archivoProgresoRelaciones)
        Catch
        End Try
        Try
            If archivoCancelarRelaciones <> "" AndAlso System.IO.File.Exists(archivoCancelarRelaciones) Then System.IO.File.Delete(archivoCancelarRelaciones)
        Catch
        End Try
        Try
            If archivoErrorRelaciones <> "" AndAlso System.IO.File.Exists(archivoErrorRelaciones) Then System.IO.File.Delete(archivoErrorRelaciones)
        Catch
        End Try
    End Sub

    Private Sub OcultarProgresoEnBreve()
        If relojOcultarProgreso Is Nothing Then
            relojOcultarProgreso = New System.Windows.Forms.Timer()
            relojOcultarProgreso.Interval = 1500
            AddHandler relojOcultarProgreso.Tick, AddressOf OcultarProgresoFinal
        End If
        relojOcultarProgreso.Stop() : relojOcultarProgreso.Start()
    End Sub

    Private Sub OcultarProgresoFinal(sender As Object, E As System.EventArgs)
        relojOcultarProgreso.Stop()
        barraProgreso.Visible = False : lblPorcentaje.Visible = False
    End Sub

    Private Sub CerrarProcesoRelaciones()
        SolicitarCancelacionRelaciones()
        If relojProcesoRelaciones IsNot Nothing Then relojProcesoRelaciones.Stop() : relojProcesoRelaciones.Dispose()
        If relojOcultarProgreso IsNot Nothing Then relojOcultarProgreso.Stop() : relojOcultarProgreso.Dispose()
        If procesoRelaciones IsNot Nothing Then
            ' Sin esperar aqui, al reabrir el buscador se perderia la referencia y
            ' se lanzaria un segundo proceso escribiendo el mismo fichero .usos.
            Try
                procesoRelaciones.WaitForExit(3000)
            Catch
            End Try
            Try
                If Not procesoRelaciones.HasExited Then procesoRelaciones.Kill()
            Catch
            End Try
            Try : procesoRelaciones.Dispose() : Catch : End Try
            procesoRelaciones = Nothing
        End If
        LimpiarArchivosTemporalesRelaciones()
    End Sub

    Private oApp As Inventor.Application

    ' --- Controles de la cabecera ---
    Private cabecera As System.Windows.Forms.Panel
    Private lblTitulo As System.Windows.Forms.Label
    Private lblSincronizado As System.Windows.Forms.Label
    Private lblPestana As System.Windows.Forms.Label
    Private btnMinimizar As System.Windows.Forms.Button
    Private btnMaximizar As System.Windows.Forms.Button
    Private btnCerrar As System.Windows.Forms.Button

    ' --- Controles del indice ---
    Private txtRuta As System.Windows.Forms.TextBox
    Private btnExaminar As System.Windows.Forms.Button
    ' Un ComboBox DropDownList ignora BackColor con los estilos visuales de
    ' Windows: siempre sale blanco. Se usa un boton con menu, que si se pinta.
    Private btnUnidad As System.Windows.Forms.Button
    Private menuUnidades As Object
    Private cboTema As System.Windows.Forms.ComboBox
    Private txtIndice As System.Windows.Forms.TextBox
    Private btnExaminarIndice As System.Windows.Forms.Button
    Private chkPartNumber As System.Windows.Forms.CheckBox
    Private btnIndexar As System.Windows.Forms.Button
    Private btnActualizar As System.Windows.Forms.Button
    Private lblIndiceInfo As System.Windows.Forms.Label

    ' --- Busqueda y filtros ---
    Private txtCodigo As System.Windows.Forms.TextBox
    Private btnLimpiar As System.Windows.Forms.Button
    Private btnBuscar As System.Windows.Forms.Button
    Private rdoTodos As System.Windows.Forms.RadioButton
    Private rdoPiezas As System.Windows.Forms.RadioButton
    Private rdoEnsamblajes As System.Windows.Forms.RadioButton
    Private rdoPlanos As System.Windows.Forms.RadioButton
    Private lblResultados As System.Windows.Forms.Label

    ' --- Resultados y acciones ---
    Private lstResultados As System.Windows.Forms.ListView
    Private panelUsos As ConsultaUsosPanel
    Private btnCancelar As System.Windows.Forms.Button
    Private btnAbrir As System.Windows.Forms.Button
    Private btnAbrirCarpeta As System.Windows.Forms.Button
    Private btnCopiar As System.Windows.Forms.Button
    Private btnMover As System.Windows.Forms.Button
    Private btnCopiarRuta As System.Windows.Forms.Button
    Private btnBorrar As System.Windows.Forms.Button
    Private lblSeleccion As System.Windows.Forms.Label
    Private lblEstado As System.Windows.Forms.Label
    Private barraProgreso As System.Windows.Forms.ProgressBar
    Private lblPorcentaje As System.Windows.Forms.Label

    ' Menu contextual creado por reflexion. No se declaran ContextMenu,
    ' ContextMenuStrip, MenuItem ni ToolStripMenuItem de forma directa para
    ' evitar errores de referencias en el compilador iLogic de Inventor 2026.
    Private menuResultados As Object
    Private mnuCopiarRuta As Object
    Private mnuCopiarFichero As Object
    Private mnuMover As Object
    Private mnuBorrar As Object
    Private mnuAbrirCarpeta As Object
    Private mnuAbrir As Object
    Private _menuContextualDisponible As Boolean = False

    Private hiloTrabajo As System.Threading.Thread
    Private cancelar As Boolean = False
    Private _cuentaIndexada As Integer = 0
    Private _progreso As Integer = 0
    Private _totalIndexar As Integer = 0
    Private _faseIndexacion As String = ""
    Private _nPiezas As Integer = 0
    Private _nEnsam As Integer = 0
    Private _nPlanos As Integer = 0
    Private _errorTrabajo As String = ""
    Private _avisosPropiedades As Integer = 0
    Private _leidosDeInventor As Integer = 0
    Private _reutilizados As Integer = 0
    Private _archivoIndexadoEnCurso As String = ""

    Private _indice As System.Collections.Generic.List(Of String())
    Private _indiceFirma As String = ""
    Private _ordenActual As Integer = 0
    Private _ascendente As Boolean = True

    ' Cache de la ultima busqueda. Los filtros por tipo trabajan sobre esta lista
    ' y no vuelven a recorrer ni a cargar los indices.
    Private _resultadosBusqueda As System.Collections.Generic.List(Of String())
    Private _codigoBusquedaActual As String = ""
    Private _resultadoTruncadoActual As Boolean = False

    ' Reloj que retrasa la busqueda automatica mientras el usuario teclea.
    Private relojBusqueda As System.Windows.Forms.Timer

    ' True solo cuando la busqueda la ha pedido el usuario (boton o Intro).
    ' La busqueda automatica al teclear nunca debe robar el foco del cuadro.
    Private _focoTrasResultados As Boolean = False

    ' Tema visual elegido por el usuario: Sistema, Normal u Oscuro.
    Private _temaSeleccionado As String = "Oscuro"

    ' Paleta activa. Se rellena en AplicarTemaActual y la reparte AplicarTemaAControl.
    Private _cFondo As Object
    Private _cCabecera As Object
    Private _cTarjeta As Object
    Private _cAcciones As Object
    Private _cEntrada As Object
    Private _cLista As Object
    Private _cBoton As Object
    Private _cTexto As Object
    Private _cTenue As Object
    Private _cBorde As Object
    Private _cAcento As Object
    Private _cTextoAcento As Object
    Private _cCerrar As Object

    Public Sub New(app As Inventor.Application)
        oApp = app
        InicializarComponentes()
        Try
            System.Windows.Forms.Application.AddMessageFilter(Me)
        Catch
        End Try
    End Sub

    ' ================= TECLADO =================
    ' Inventor se queda con Intro y Escape cuando el formulario no es modal, asi
    ' que se cablean por cuatro vias distintas. Ninguna es imprescindible: la
    ' busqueda se lanza sola al teclear y la ventana se cierra con el boton X.

    ' Con un desplegable abierto, Escape debe cerrar el desplegable, no la ventana.
    Private Function DesplegableAbierto() As Boolean
        Try
            Dim combo As System.Windows.Forms.ComboBox = _
                TryCast(Me.ActiveControl, System.Windows.Forms.ComboBox)
            Return combo IsNot Nothing AndAlso combo.DroppedDown
        Catch
            Return False
        End Try
    End Function

    Protected Overrides Function ProcessCmdKey(ByRef msg As System.Windows.Forms.Message, _
            keyData As System.Windows.Forms.Keys) As Boolean
        If keyData <> System.Windows.Forms.Keys.Escape AndAlso _
                keyData <> System.Windows.Forms.Keys.Enter AndAlso _
                keyData <> System.Windows.Forms.Keys.Return Then
            Return MyBase.ProcessCmdKey(msg, keyData)
        End If
        Dim tecla As System.Windows.Forms.Keys = keyData And System.Windows.Forms.Keys.KeyCode
        If tecla = System.Windows.Forms.Keys.Escape AndAlso DesplegableAbierto() Then
            Return MyBase.ProcessCmdKey(msg, keyData)
        End If
        If tecla = System.Windows.Forms.Keys.Escape Then
            CerrarBuscador()
            Return True
        End If
        If tecla = System.Windows.Forms.Keys.Enter OrElse tecla = System.Windows.Forms.Keys.Return Then
            If txtCodigo IsNot Nothing AndAlso txtCodigo.Focused Then
                EjecutarBusquedaDesdeCodigo()
                Return True
            End If
        End If
        Return MyBase.ProcessCmdKey(msg, keyData)
    End Function

    Protected Overrides Function ProcessDialogKey(keyData As System.Windows.Forms.Keys) As Boolean
        Dim tecla As System.Windows.Forms.Keys = keyData And System.Windows.Forms.Keys.KeyCode
        If tecla = System.Windows.Forms.Keys.Escape Then
            CerrarBuscador()
            Return True
        End If
        If tecla = System.Windows.Forms.Keys.Enter OrElse tecla = System.Windows.Forms.Keys.Return Then
            If txtCodigo IsNot Nothing AndAlso txtCodigo.Focused Then
                EjecutarBusquedaDesdeCodigo()
                Return True
            End If
        End If
        Return MyBase.ProcessDialogKey(keyData)
    End Function

    Public Function PreFilterMessage(ByRef mensaje As System.Windows.Forms.Message) As Boolean _
            Implements System.Windows.Forms.IMessageFilter.PreFilterMessage
        Const WM_KEYDOWN As Integer = &H100
        If mensaje.Msg <> WM_KEYDOWN Then Return False
        If Not Me.Visible OrElse Me.IsDisposed Then Return False
        If System.Windows.Forms.Control.ModifierKeys <> System.Windows.Forms.Keys.None Then Return False
        Dim codigo As Long = mensaje.WParam.ToInt64()
        If codigo = CLng(System.Windows.Forms.Keys.Escape) Then
            If DesplegableAbierto() Then Return False
            If Me.ContainsFocus Then
                CerrarBuscador()
                Return True
            End If
            Return False
        End If
        If codigo <> CLng(System.Windows.Forms.Keys.Enter) Then Return False
        If txtCodigo Is Nothing OrElse Not txtCodigo.Focused Then Return False
        EjecutarBusquedaDesdeCodigo()
        Return True
    End Function

    Private Sub OnFormularioKeyDown(sender As Object, e As System.Windows.Forms.KeyEventArgs)
        If e.KeyCode = System.Windows.Forms.Keys.Escape Then
            e.Handled = True : e.SuppressKeyPress = True
            CerrarBuscador()
        ElseIf e.KeyCode = System.Windows.Forms.Keys.Enter Then
            If txtCodigo IsNot Nothing AndAlso txtCodigo.Focused Then
                e.Handled = True : e.SuppressKeyPress = True
                EjecutarBusquedaDesdeCodigo()
            End If
        End If
    End Sub

    Private Sub OnCodigoPreviewKeyDown(sender As Object, e As System.Windows.Forms.PreviewKeyDownEventArgs)
        If e.KeyCode = System.Windows.Forms.Keys.Enter OrElse e.KeyCode = System.Windows.Forms.Keys.Return Then
            e.IsInputKey = True
        End If
    End Sub

    Private Sub OnCodigoKeyDown(sender As Object, e As System.Windows.Forms.KeyEventArgs)
        If e.KeyCode = System.Windows.Forms.Keys.Enter OrElse e.KeyCode = System.Windows.Forms.Keys.Return Then
            EjecutarBusquedaDesdeCodigo()
            e.Handled = True
            e.SuppressKeyPress = True
        ElseIf e.KeyCode = System.Windows.Forms.Keys.Escape Then
            e.Handled = True
            e.SuppressKeyPress = True
            CerrarBuscador()
        End If
    End Sub

    Private Sub EjecutarBusquedaDesdeCodigo()
        If txtCodigo Is Nothing OrElse btnBuscar Is Nothing Then Return
        If Not btnBuscar.Enabled Then Return
        DetenerRelojBusqueda()
        OnBuscar(btnBuscar, System.EventArgs.Empty)
    End Sub

    Private Sub CerrarBuscador()
        If HayIndexacionActiva() Then cancelar = True
        Try
            Me.Close()
        Catch
        End Try
    End Sub

    ' ================= BUSQUEDA AUTOMATICA =================
    ' Es la via principal: no depende de que Inventor suelte la tecla Intro.
    Private Sub DetenerRelojBusqueda()
        If relojBusqueda IsNot Nothing Then relojBusqueda.Stop()
    End Sub

    Private Sub LiberarRelojBusqueda()
        If relojBusqueda Is Nothing Then Return
        Try
            relojBusqueda.Stop()
            relojBusqueda.Dispose()
        Catch
        End Try
        relojBusqueda = Nothing
    End Sub

    Private Sub OnCodigoTextChanged(sender As Object, e As System.EventArgs)
        If btnLimpiar IsNot Nothing Then btnLimpiar.Visible = (txtCodigo.Text.Length > 0)
        If relojBusqueda Is Nothing Then
            relojBusqueda = New System.Windows.Forms.Timer()
            relojBusqueda.Interval = RETARDO_BUSQUEDA
            AddHandler relojBusqueda.Tick, AddressOf OnBusquedaAutomatica
        End If
        relojBusqueda.Stop()
        If IndexandoAhora() Then Return
        If txtCodigo.Text.Trim().Length >= MINIMO_BUSQUEDA Then relojBusqueda.Start()
    End Sub

    Private Sub OnBusquedaAutomatica(sender As Object, e As System.EventArgs)
        relojBusqueda.Stop()
        If Me.IsDisposed OrElse cerradoDatos Then Return
        If IndexandoAhora() Then Return
        Dim codigo As String = txtCodigo.Text.Trim()
        If codigo.Length < MINIMO_BUSQUEDA Then Return
        If String.Equals(codigo, _codigoBusquedaActual, System.StringComparison.OrdinalIgnoreCase) Then Return
        If Not btnBuscar.Enabled Then Return
        _focoTrasResultados = False
        If panelUsos IsNot Nothing Then panelUsos.CambiarCarpeta(CarpetaIndice())
        PedirDatos(codigo)
    End Sub

    Private Sub OnLimpiarBusqueda(sender As Object, e As System.EventArgs)
        DetenerRelojBusqueda()
        txtCodigo.Text = ""
        txtCodigo.Select()
    End Sub

    ' ================= VENTANA SIN BORDES =================
    Private Sub OnArrastrarVentana(sender As Object, e As System.Windows.Forms.MouseEventArgs)
        If e.Button <> System.Windows.Forms.MouseButtons.Left Then Return
        If Me.WindowState = System.Windows.Forms.FormWindowState.Maximized Then Return
        Const WM_NCLBUTTONDOWN As Integer = &HA1
        Const HTCAPTION As Integer = 2
        Try
            ReleaseCapture()
            SendMessage(Me.Handle, WM_NCLBUTTONDOWN, HTCAPTION, 0)
        Catch
        End Try
    End Sub

    Private Sub OnRedimensionarVentana(sender As Object, e As System.Windows.Forms.MouseEventArgs)
        If e.Button <> System.Windows.Forms.MouseButtons.Left Then Return
        Const WM_NCLBUTTONDOWN As Integer = &HA1
        Const HTBOTTOMRIGHT As Integer = 17
        Try
            ReleaseCapture()
            SendMessage(Me.Handle, WM_NCLBUTTONDOWN, HTBOTTOMRIGHT, 0)
        Catch
        End Try
    End Sub

    Private Sub OnCabeceraDobleClic(sender As Object, e As System.Windows.Forms.MouseEventArgs)
        AlternarMaximizado()
    End Sub

    ' MinimumSize necesitaria un Size de System.Drawing, asi que se limita a mano.
    Private Sub OnLimitarTamano(sender As Object, e As System.EventArgs)
        If Me.WindowState <> System.Windows.Forms.FormWindowState.Normal Then Return
        If Me.Width < 980 Then Me.Width = 980
        If Me.Height < 560 Then Me.Height = 560
    End Sub

    Private Sub OnMinimizarVentana(sender As Object, e As System.EventArgs)
        Me.WindowState = System.Windows.Forms.FormWindowState.Minimized
    End Sub

    Private Sub OnMaximizarVentana(sender As Object, e As System.EventArgs)
        AlternarMaximizado()
    End Sub

    Private Sub AlternarMaximizado()
        If Me.WindowState = System.Windows.Forms.FormWindowState.Maximized Then
            Me.WindowState = System.Windows.Forms.FormWindowState.Normal
        Else
            Me.WindowState = System.Windows.Forms.FormWindowState.Maximized
        End If
    End Sub

    Private Sub OnCerrarVentana(sender As Object, e As System.EventArgs)
        CerrarBuscador()
    End Sub

    Private Function CarpetaConfig() As String
        Return System.IO.Path.Combine( _
            System.Environment.GetFolderPath(System.Environment.SpecialFolder.MyDocuments), _
            "BuscadorInventor")
    End Function

    ' ================= INTERFAZ =================
    Private Sub InicializarComponentes()
        Me.Text = "Buscador CAD - Indice de busqueda v7.9.2"
        ' El borde va PRIMERO: al cambiarlo despues, WinForms conserva el area
        ' cliente y la ventana se queda ~39 px mas corta, cortando las barras
        ' de abajo.
        Me.FormBorderStyle = System.Windows.Forms.FormBorderStyle.None
        Me.Width = 1320
        Me.Height = 742
        Me.StartPosition = System.Windows.Forms.FormStartPosition.CenterScreen
        Me.ShowInTaskbar = True
        Me.KeyPreview = True

        CrearCabecera()
        CrearBarraIndice()
        CrearCajaBusqueda()
        CrearFiltros()
        CrearListaResultados()
        CrearPanelUsos()
        CrearProgreso()
        CrearBarraAcciones()
        CrearBarraInferior()

        AddHandler Me.FormClosing, AddressOf OnFormularioClosing
        AddHandler Me.Shown, AddressOf OnFormularioShown
        AddHandler Me.Activated, AddressOf OnFormularioActivated
        AddHandler Me.KeyDown, AddressOf OnFormularioKeyDown
        AddHandler Me.Resize, AddressOf OnLimitarTamano
        AddHandler txtIndice.Validated, AddressOf OnIndiceValidado

        Me.AcceptButton = btnBuscar

        CargarAjustes()
        panelUsos.CambiarCarpeta(CarpetaIndice())
        AplicarTemaActual()
        ActualizarInfoIndice()
        ActualizarSeleccion()
    End Sub

    Private Function Etiqueta(texto As String, x As Integer, y As Integer, w As Integer) _
            As System.Windows.Forms.Label
        Dim l As New System.Windows.Forms.Label()
        l.Text = texto : l.Left = x : l.Top = y : l.Width = w
        Return l
    End Function

    Private Function EtiquetaTenue(texto As String, x As Integer, y As Integer, w As Integer) _
            As System.Windows.Forms.Label
        Dim l As System.Windows.Forms.Label = Etiqueta(texto, x, y, w)
        l.Tag = "TENUE"
        Return l
    End Function

    Private Function Boton(texto As String, x As Integer, y As Integer, w As Integer, _
            h As Integer, anclaje As System.Windows.Forms.AnchorStyles) As System.Windows.Forms.Button
        Dim b As New System.Windows.Forms.Button()
        b.Text = texto : b.Left = x : b.Top = y : b.Width = w : b.Height = h : b.Anchor = anclaje
        b.TabStop = False
        Return b
    End Function

    ' El TextBox va dentro de un panel que hace de caja. Asi el alto lo fijamos
    ' nosotros y ni el cambio de BorderStyle ni el de fuente pueden recortar el
    ' texto, que era lo que dejaba los campos a medias.
    Private Function CampoTexto(caja As System.Windows.Forms.TextBox, _
            x As Integer, y As Integer, w As Integer, h As Integer, _
            anclaje As System.Windows.Forms.AnchorStyles) As System.Windows.Forms.Panel
        Dim marco As New System.Windows.Forms.Panel()
        marco.Left = x : marco.Top = y : marco.Width = w : marco.Height = h
        marco.Tag = "CAMPO" : marco.Anchor = anclaje
        marco.Padding = New System.Windows.Forms.Padding(6, 3, 6, 3)
        caja.BorderStyle = System.Windows.Forms.BorderStyle.None
        caja.Dock = System.Windows.Forms.DockStyle.Fill
        marco.Controls.Add(caja)
        Return marco
    End Function

    Private Function Tarjeta(x As Integer, y As Integer, w As Integer, h As Integer, _
            marca As String, anclaje As System.Windows.Forms.AnchorStyles) As System.Windows.Forms.Panel
        Dim p As New System.Windows.Forms.Panel()
        p.Left = x : p.Top = y : p.Width = w : p.Height = h
        p.Tag = marca : p.Anchor = anclaje
        Return p
    End Function

    Private Sub CrearCabecera()
        Dim anclaBarra As System.Windows.Forms.AnchorStyles = _
            System.Windows.Forms.AnchorStyles.Top Or System.Windows.Forms.AnchorStyles.Left _
            Or System.Windows.Forms.AnchorStyles.Right
        Dim anclaDerecha As System.Windows.Forms.AnchorStyles = _
            System.Windows.Forms.AnchorStyles.Top Or System.Windows.Forms.AnchorStyles.Right

        cabecera = Tarjeta(0, 0, 1320, 44, "CABECERA", anclaBarra)
        AddHandler cabecera.MouseDown, AddressOf OnArrastrarVentana
        AddHandler cabecera.MouseDoubleClick, AddressOf OnCabeceraDobleClic

        lblTitulo = Etiqueta("BUSCADOR CAD", 20, 13, 160)
        lblTitulo.Tag = "TITULO"
        AddHandler lblTitulo.MouseDown, AddressOf OnArrastrarVentana
        cabecera.Controls.Add(lblTitulo)

        cabecera.Controls.Add(EtiquetaTenue("v7.9.2", 182, 16, 40))

        lblSincronizado = Etiqueta("   Indice sincronizado", 232, 10, 210)
        lblSincronizado.Height = 24
        lblSincronizado.BorderStyle = System.Windows.Forms.BorderStyle.FixedSingle
        lblSincronizado.Tag = "PILDORA"
        cabecera.Controls.Add(lblSincronizado)

        lblPestana = Etiqueta("INDICE DE BUSQUEDA", 570, 14, 200)
        lblPestana.Tag = "PESTANA"
        AddHandler lblPestana.MouseDown, AddressOf OnArrastrarVentana
        cabecera.Controls.Add(lblPestana)

        btnMinimizar = Boton("–", 1196, 10, 30, 24, anclaDerecha)
        AddHandler btnMinimizar.Click, AddressOf OnMinimizarVentana
        cabecera.Controls.Add(btnMinimizar)

        btnMaximizar = Boton("□", 1230, 10, 30, 24, anclaDerecha)
        AddHandler btnMaximizar.Click, AddressOf OnMaximizarVentana
        cabecera.Controls.Add(btnMaximizar)

        btnCerrar = Boton("X", 1264, 10, 30, 24, anclaDerecha)
        btnCerrar.Tag = "CERRAR"
        AddHandler btnCerrar.Click, AddressOf OnCerrarVentana
        cabecera.Controls.Add(btnCerrar)

        ' El selector de tema se conserva por compatibilidad con los ajustes
        ' guardados, pero la v7.6 va siempre en oscuro.
        cboTema = New System.Windows.Forms.ComboBox()
        cboTema.DropDownStyle = System.Windows.Forms.ComboBoxStyle.DropDownList
        cboTema.Items.Add("Sistema") : cboTema.Items.Add("Normal") : cboTema.Items.Add("Oscuro")
        cboTema.Left = 0 : cboTema.Top = 0 : cboTema.Width = 80
        cboTema.Visible = False
        AddHandler cboTema.SelectedIndexChanged, AddressOf OnTemaChanged
        cabecera.Controls.Add(cboTema)

        Me.Controls.Add(cabecera)
    End Sub

    Private Sub CrearBarraIndice()
        Dim anclaBarra As System.Windows.Forms.AnchorStyles = _
            System.Windows.Forms.AnchorStyles.Top Or System.Windows.Forms.AnchorStyles.Left _
            Or System.Windows.Forms.AnchorStyles.Right
        Dim anclaIzquierda As System.Windows.Forms.AnchorStyles = _
            System.Windows.Forms.AnchorStyles.Top Or System.Windows.Forms.AnchorStyles.Left
        Dim anclaDerecha As System.Windows.Forms.AnchorStyles = _
            System.Windows.Forms.AnchorStyles.Top Or System.Windows.Forms.AnchorStyles.Right

        Dim panelIndice As System.Windows.Forms.Panel = Tarjeta(24, 56, 1272, 64, "TARJETA", anclaBarra)
        panelIndice.BorderStyle = System.Windows.Forms.BorderStyle.FixedSingle

        panelIndice.Controls.Add(EtiquetaTenue("UNIDAD", 14, 9, 70))
        btnUnidad = Boton("Elegir...", 14, 25, 120, 24, anclaIzquierda)
        AddHandler btnUnidad.Click, AddressOf OnElegirUnidad
        panelIndice.Controls.Add(btnUnidad)
        CrearMenuUnidades()

        panelIndice.Controls.Add(EtiquetaTenue("CARPETA A INDEXAR", 148, 9, 160))
        txtRuta = New System.Windows.Forms.TextBox()
        panelIndice.Controls.Add(CampoTexto(txtRuta, 148, 25, 300, 24, anclaIzquierda))
        btnExaminar = Boton("...", 452, 26, 34, 22, anclaIzquierda)
        AddHandler btnExaminar.Click, AddressOf OnExaminarRuta
        panelIndice.Controls.Add(btnExaminar)

        panelIndice.Controls.Add(EtiquetaTenue("CARPETA DEL INDICE", 500, 9, 160))
        txtIndice = New System.Windows.Forms.TextBox()
        AddHandler txtIndice.TextChanged, AddressOf OnIndiceCarpetaChanged
        panelIndice.Controls.Add(CampoTexto(txtIndice, 500, 25, 320, 24, anclaIzquierda))
        btnExaminarIndice = Boton("...", 824, 26, 34, 22, anclaIzquierda)
        AddHandler btnExaminarIndice.Click, AddressOf OnExaminarIndice
        panelIndice.Controls.Add(btnExaminarIndice)

        lblIndiceInfo = EtiquetaTenue("", 872, 9, 210)
        panelIndice.Controls.Add(lblIndiceInfo)

        chkPartNumber = New System.Windows.Forms.CheckBox()
        chkPartNumber.Text = "Nº de pieza y descripcion"
        chkPartNumber.Left = 872 : chkPartNumber.Top = 26 : chkPartNumber.Width = 210
        chkPartNumber.Checked = False
        AddHandler chkPartNumber.CheckedChanged, AddressOf OnMetadatosChanged
        panelIndice.Controls.Add(chkPartNumber)

        btnIndexar = Boton("Reindexar", 1090, 25, 85, 26, anclaDerecha)
        AddHandler btnIndexar.Click, AddressOf OnIndexar
        panelIndice.Controls.Add(btnIndexar)

        btnActualizar = Boton("Actualizar", 1181, 25, 85, 26, anclaDerecha)
        AddHandler btnActualizar.Click, AddressOf OnActualizar
        panelIndice.Controls.Add(btnActualizar)

        Me.Controls.Add(panelIndice)
    End Sub

    Private Sub CrearCajaBusqueda()
        Dim anclaBarra As System.Windows.Forms.AnchorStyles = _
            System.Windows.Forms.AnchorStyles.Top Or System.Windows.Forms.AnchorStyles.Left _
            Or System.Windows.Forms.AnchorStyles.Right
        Dim anclaDerecha As System.Windows.Forms.AnchorStyles = _
            System.Windows.Forms.AnchorStyles.Top Or System.Windows.Forms.AnchorStyles.Right

        Dim caja As System.Windows.Forms.Panel = Tarjeta(24, 130, 1272, 46, "BUSQUEDA", anclaBarra)
        caja.BorderStyle = System.Windows.Forms.BorderStyle.FixedSingle

        caja.Controls.Add(EtiquetaTenue("CODIGO", 14, 16, 60))

        txtCodigo = New System.Windows.Forms.TextBox()
        AddHandler txtCodigo.TextChanged, AddressOf OnCodigoTextChanged
        AddHandler txtCodigo.PreviewKeyDown, AddressOf OnCodigoPreviewKeyDown
        AddHandler txtCodigo.KeyDown, AddressOf OnCodigoKeyDown
        caja.Controls.Add(CampoTexto(txtCodigo, 78, 9, 1000, 28, anclaBarra))

        btnLimpiar = Boton("X", 1086, 11, 26, 22, anclaDerecha)
        btnLimpiar.Visible = False
        AddHandler btnLimpiar.Click, AddressOf OnLimpiarBusqueda
        caja.Controls.Add(btnLimpiar)

        btnBuscar = Boton("Buscar", 1120, 9, 140, 26, anclaDerecha)
        AddHandler btnBuscar.Click, AddressOf OnBuscar
        caja.Controls.Add(btnBuscar)

        Me.Controls.Add(caja)
    End Sub

    Private Sub CrearFiltros()
        rdoTodos = New System.Windows.Forms.RadioButton()
        rdoTodos.Text = "Todos" : rdoTodos.Checked = True
        rdoTodos.Left = 26 : rdoTodos.Top = 186 : rdoTodos.Width = 90
        AddHandler rdoTodos.CheckedChanged, AddressOf OnFiltroTipoChanged
        Me.Controls.Add(rdoTodos)

        rdoPiezas = New System.Windows.Forms.RadioButton()
        rdoPiezas.Text = ".ipt  Piezas"
        rdoPiezas.Left = 120 : rdoPiezas.Top = 186 : rdoPiezas.Width = 120
        AddHandler rdoPiezas.CheckedChanged, AddressOf OnFiltroTipoChanged
        Me.Controls.Add(rdoPiezas)

        rdoEnsamblajes = New System.Windows.Forms.RadioButton()
        rdoEnsamblajes.Text = ".iam  Ensamblajes"
        rdoEnsamblajes.Left = 248 : rdoEnsamblajes.Top = 186 : rdoEnsamblajes.Width = 170
        AddHandler rdoEnsamblajes.CheckedChanged, AddressOf OnFiltroTipoChanged
        Me.Controls.Add(rdoEnsamblajes)

        rdoPlanos = New System.Windows.Forms.RadioButton()
        rdoPlanos.Text = ".idw  Planos"
        rdoPlanos.Left = 424 : rdoPlanos.Top = 186 : rdoPlanos.Width = 140
        AddHandler rdoPlanos.CheckedChanged, AddressOf OnFiltroTipoChanged
        Me.Controls.Add(rdoPlanos)

        lblResultados = EtiquetaTenue("Sin busqueda", 980, 188, 316)
        lblResultados.Anchor = System.Windows.Forms.AnchorStyles.Top Or System.Windows.Forms.AnchorStyles.Right
        Me.Controls.Add(lblResultados)
    End Sub

    ' Etiqueta de cabecera de tabla: texto oscuro sobre ambar y clic para
    ' ordenar. El indice de columna viaja en Name porque Tag lo usa el tema.
    Private Function EtiquetaColumna(texto As String, columna As Integer, _
            x As Integer, w As Integer, _
            anclaje As System.Windows.Forms.AnchorStyles) As System.Windows.Forms.Label
        Dim l As New System.Windows.Forms.Label()
        l.Text = texto : l.Left = x : l.Top = 7 : l.Width = w
        l.Tag = "TEXTOACENTO" : l.Name = "COL" & columna.ToString()
        l.Anchor = anclaje
        l.Cursor = System.Windows.Forms.Cursors.Hand
        AddHandler l.Click, AddressOf OnCabeceraTablaClic
        Return l
    End Function

    Private Sub OnCabeceraTablaClic(sender As Object, e As System.EventArgs)
        Dim rotulo As System.Windows.Forms.Label = _
            TryCast(sender, System.Windows.Forms.Label)
        If rotulo Is Nothing Then Return
        Dim columna As Integer = 0
        If Not Integer.TryParse(rotulo.Name.Replace("COL", ""), columna) Then Return
        OrdenarPorColumna(columna)
    End Sub

    Private Sub CrearListaResultados()
        Dim anclaCabecera As System.Windows.Forms.AnchorStyles = _
            System.Windows.Forms.AnchorStyles.Top Or System.Windows.Forms.AnchorStyles.Left _
            Or System.Windows.Forms.AnchorStyles.Right
        Dim anclaFija As System.Windows.Forms.AnchorStyles = _
            System.Windows.Forms.AnchorStyles.Top Or System.Windows.Forms.AnchorStyles.Left

        ' La cabecera del sistema no admite color, asi que se oculta y se pone
        ' esta encima, hecha con controles normales que si sabemos pintar.
        Dim cabeceraTabla As System.Windows.Forms.Panel = _
            Tarjeta(24, 212, 856, 26, "CABTABLA", anclaCabecera)
        cabeceraTabla.Controls.Add(EtiquetaColumna("CODIGO Y NOMBRE DEL FICHERO", 0, 6, 350, anclaFija))
        cabeceraTabla.Controls.Add(EtiquetaColumna("FORMATO", 1, 366, 74, anclaFija))
        cabeceraTabla.Controls.Add(EtiquetaColumna("MODIFICADO", 2, 446, 124, anclaFija))
        cabeceraTabla.Controls.Add(EtiquetaColumna("RUTA COMPARTIDA", 3, 576, 260, anclaFija))
        Me.Controls.Add(cabeceraTabla)

        lstResultados = New System.Windows.Forms.ListView()
        lstResultados.Left = 24 : lstResultados.Top = 238
        lstResultados.Width = 856 : lstResultados.Height = 354
        lstResultados.View = System.Windows.Forms.View.Details
        lstResultados.FullRowSelect = True
        lstResultados.MultiSelect = True
        lstResultados.HideSelection = False
        lstResultados.GridLines = False
        lstResultados.Anchor = System.Windows.Forms.AnchorStyles.Top _
            Or System.Windows.Forms.AnchorStyles.Bottom _
            Or System.Windows.Forms.AnchorStyles.Left _
            Or System.Windows.Forms.AnchorStyles.Right
        lstResultados.Columns.Add("CODIGO Y NOMBRE DEL FICHERO", 360)
        lstResultados.Columns.Add("FORMATO", 80)
        lstResultados.Columns.Add("MODIFICADO", 130)
        lstResultados.Columns.Add("RUTA COMPARTIDA", 265)
        AddHandler lstResultados.DoubleClick, AddressOf OnAbrir
        AddHandler lstResultados.ColumnClick, AddressOf OnColumnClick
        AddHandler lstResultados.KeyDown, AddressOf OnResultadosKeyDown
        AddHandler lstResultados.SelectedIndexChanged, AddressOf OnSeleccionResultadosChanged
        AddHandler lstResultados.MouseDown, AddressOf OnResultadosMouseDown
        lstResultados.HeaderStyle = System.Windows.Forms.ColumnHeaderStyle.None
        CrearMenuContextualResultados()
        Me.Controls.Add(lstResultados)
    End Sub

    Private Sub CrearPanelUsos()
        panelUsos = New ConsultaUsosPanel(oApp)
        panelUsos.Left = 892 : panelUsos.Top = 212
        panelUsos.Width = 404 : panelUsos.Height = 380
        panelUsos.Anchor = System.Windows.Forms.AnchorStyles.Top _
            Or System.Windows.Forms.AnchorStyles.Bottom _
            Or System.Windows.Forms.AnchorStyles.Right
        Me.Controls.Add(panelUsos)
    End Sub

    Private Sub CrearProgreso()
        barraProgreso = New System.Windows.Forms.ProgressBar()
        barraProgreso.Left = 24 : barraProgreso.Top = 600
        barraProgreso.Width = 1200 : barraProgreso.Height = 14
        barraProgreso.Minimum = 0 : barraProgreso.Maximum = 100
        barraProgreso.Anchor = System.Windows.Forms.AnchorStyles.Bottom _
            Or System.Windows.Forms.AnchorStyles.Left Or System.Windows.Forms.AnchorStyles.Right
        barraProgreso.Visible = False
        Me.Controls.Add(barraProgreso)

        lblPorcentaje = EtiquetaTenue("0 %", 1232, 598, 64)
        lblPorcentaje.Height = 18
        lblPorcentaje.Anchor = System.Windows.Forms.AnchorStyles.Bottom Or System.Windows.Forms.AnchorStyles.Right
        lblPorcentaje.Visible = False
        Me.Controls.Add(lblPorcentaje)

        lblEstado = Etiqueta("Listo.", 24, 622, 1272)
        lblEstado.Anchor = System.Windows.Forms.AnchorStyles.Bottom _
            Or System.Windows.Forms.AnchorStyles.Left Or System.Windows.Forms.AnchorStyles.Right
        Me.Controls.Add(lblEstado)
    End Sub

    Private Sub CrearBarraAcciones()
        Dim anclaBarra As System.Windows.Forms.AnchorStyles = _
            System.Windows.Forms.AnchorStyles.Bottom Or System.Windows.Forms.AnchorStyles.Left _
            Or System.Windows.Forms.AnchorStyles.Right
        Dim anclaDerecha As System.Windows.Forms.AnchorStyles = _
            System.Windows.Forms.AnchorStyles.Top Or System.Windows.Forms.AnchorStyles.Right

        Dim acciones As System.Windows.Forms.Panel = Tarjeta(24, 648, 1272, 64, "ACCIONES", anclaBarra)
        acciones.BorderStyle = System.Windows.Forms.BorderStyle.FixedSingle

        lblSeleccion = Etiqueta("Ningun fichero seleccionado", 14, 11, 340)
        acciones.Controls.Add(lblSeleccion)
        ' 340 y no mas: con 400 llegaba a x=414 y se solapaba con btnCancelar
        ' (x=393). Al anadirse antes que el boton, la etiqueta queda por delante
        ' en el orden Z y le pintaba encima el borde izquierdo.
        acciones.Controls.Add(EtiquetaTenue( _
            "Intro: abrir    Ctrl+C: copiar ruta    Supr: borrar", 14, 34, 340))

        btnCancelar = Boton("Cancelar", 393, 17, 95, 30, anclaDerecha)
        btnCancelar.Enabled = False
        AddHandler btnCancelar.Click, AddressOf OnCancelar
        acciones.Controls.Add(btnCancelar)

        btnCopiarRuta = Boton("Copiar ruta", 496, 17, 110, 30, anclaDerecha)
        AddHandler btnCopiarRuta.Click, AddressOf OnCopiarRuta
        acciones.Controls.Add(btnCopiarRuta)

        btnCopiar = Boton("Copiar fichero", 614, 17, 125, 30, anclaDerecha)
        AddHandler btnCopiar.Click, AddressOf OnCopiarFicheros
        acciones.Controls.Add(btnCopiar)

        btnMover = Boton("Mover", 747, 17, 90, 30, anclaDerecha)
        AddHandler btnMover.Click, AddressOf OnMoverFicheros
        acciones.Controls.Add(btnMover)

        btnBorrar = Boton("Borrar", 845, 17, 90, 30, anclaDerecha)
        AddHandler btnBorrar.Click, AddressOf OnBorrarFicheros
        acciones.Controls.Add(btnBorrar)

        btnAbrirCarpeta = Boton("Explorar carpeta", 943, 17, 140, 30, anclaDerecha)
        AddHandler btnAbrirCarpeta.Click, AddressOf OnAbrirCarpeta
        acciones.Controls.Add(btnAbrirCarpeta)

        btnAbrir = Boton("Abrir en Inventor", 1091, 17, 165, 30, anclaDerecha)
        btnAbrir.Tag = "ACENTO"
        AddHandler btnAbrir.Click, AddressOf OnAbrir
        acciones.Controls.Add(btnAbrir)

        ' Cinturon: ninguna etiqueta puede volver a taparlos.
        btnCancelar.BringToFront() : btnCopiarRuta.BringToFront()
        btnCopiar.BringToFront() : btnMover.BringToFront()
        btnBorrar.BringToFront() : btnAbrirCarpeta.BringToFront()
        btnAbrir.BringToFront()

        Me.Controls.Add(acciones)
    End Sub

    Private Sub CrearBarraInferior()
        Dim anclaBarra As System.Windows.Forms.AnchorStyles = _
            System.Windows.Forms.AnchorStyles.Bottom Or System.Windows.Forms.AnchorStyles.Left _
            Or System.Windows.Forms.AnchorStyles.Right
        Dim anclaDerecha As System.Windows.Forms.AnchorStyles = _
            System.Windows.Forms.AnchorStyles.Bottom Or System.Windows.Forms.AnchorStyles.Right

        Dim inferior As System.Windows.Forms.Panel = Tarjeta(0, 716, 1320, 26, "ESTADO", anclaBarra)
        inferior.Controls.Add(EtiquetaTenue("ESC   Cerrar", 24, 6, 110))
        inferior.Controls.Add(EtiquetaTenue("INTRO   Abrir", 144, 6, 115))
        inferior.Controls.Add(EtiquetaTenue("CTRL+C   Copiar ruta", 268, 6, 165))
        inferior.Controls.Add(EtiquetaTenue("SUPR   Borrar", 442, 6, 120))

        Dim lblTipos As System.Windows.Forms.Label = EtiquetaTenue("IPT / IAM / IDW", 1050, 6, 120)
        lblTipos.Anchor = anclaDerecha
        inferior.Controls.Add(lblTipos)

        Dim lblGrip As System.Windows.Forms.Label = EtiquetaTenue("///", 1290, 6, 26)
        lblGrip.Anchor = anclaDerecha
        lblGrip.Cursor = System.Windows.Forms.Cursors.SizeNWSE
        AddHandler lblGrip.MouseDown, AddressOf OnRedimensionarVentana
        inferior.Controls.Add(lblGrip)

        Me.Controls.Add(inferior)
    End Sub

    ' Crea el menu que aparece al pulsar el boton derecho sobre los resultados.
    ' Se instancia por reflexion para que iLogic no tenga que resolver en
    ' compilacion los tipos ContextMenuStrip/ToolStripMenuItem ni System.Drawing.
    Private Sub CrearMenuContextualResultados()
        _menuContextualDisponible = False
        menuResultados = Nothing

        Try
            Dim ensambladoWinForms As System.Reflection.Assembly = _
                GetType(System.Windows.Forms.Form).Assembly

            Dim tipoMenu As System.Type = ensambladoWinForms.GetType( _
                "System.Windows.Forms.ContextMenuStrip", False)
            Dim tipoItem As System.Type = ensambladoWinForms.GetType( _
                "System.Windows.Forms.ToolStripMenuItem", False)
            Dim tipoSeparador As System.Type = ensambladoWinForms.GetType( _
                "System.Windows.Forms.ToolStripSeparator", False)

            If tipoMenu Is Nothing OrElse tipoItem Is Nothing Then Return

            menuResultados = System.Activator.CreateInstance(tipoMenu)
            mnuCopiarRuta = CrearElementoMenuReflexion(tipoItem, _
                "Copiar ruta", New System.EventHandler(AddressOf OnCopiarRuta))
            mnuCopiarFichero = CrearElementoMenuReflexion(tipoItem, _
                "Copiar fichero", New System.EventHandler(AddressOf OnCopiarFicheros))
            mnuMover = CrearElementoMenuReflexion(tipoItem, _
                "Mover", New System.EventHandler(AddressOf OnMoverFicheros))
            mnuBorrar = CrearElementoMenuReflexion(tipoItem, _
                "Borrar", New System.EventHandler(AddressOf OnBorrarFicheros))
            mnuAbrirCarpeta = CrearElementoMenuReflexion(tipoItem, _
                "Explorar carpeta", New System.EventHandler(AddressOf OnAbrirCarpeta))
            mnuAbrir = CrearElementoMenuReflexion(tipoItem, _
                "Abrir en Inventor", New System.EventHandler(AddressOf OnAbrir))

            AgregarElementoMenuReflexion(menuResultados, mnuCopiarRuta)
            AgregarElementoMenuReflexion(menuResultados, mnuCopiarFichero)
            AgregarElementoMenuReflexion(menuResultados, mnuMover)
            AgregarElementoMenuReflexion(menuResultados, mnuBorrar)

            If tipoSeparador IsNot Nothing Then
                Dim separador As Object = System.Activator.CreateInstance(tipoSeparador)
                AgregarElementoMenuReflexion(menuResultados, separador)
            End If

            AgregarElementoMenuReflexion(menuResultados, mnuAbrirCarpeta)
            AgregarElementoMenuReflexion(menuResultados, mnuAbrir)

            Dim propiedadMenu As System.Reflection.PropertyInfo = _
                GetType(System.Windows.Forms.Control).GetProperty("ContextMenuStrip")
            If propiedadMenu Is Nothing OrElse Not propiedadMenu.CanWrite Then Return

            propiedadMenu.SetValue(lstResultados, menuResultados, Nothing)
            _menuContextualDisponible = True
            ActualizarEstadoMenuContextual()

        Catch
            _menuContextualDisponible = False
            menuResultados = Nothing
        End Try
    End Sub

    Private Function CrearElementoMenuReflexion(tipoItem As System.Type, _
            texto As String, manejador As System.EventHandler) As Object
        Dim item As Object = System.Activator.CreateInstance(tipoItem)

        Dim propiedadTexto As System.Reflection.PropertyInfo = _
            tipoItem.GetProperty("Text")
        If propiedadTexto IsNot Nothing AndAlso propiedadTexto.CanWrite Then
            propiedadTexto.SetValue(item, texto, Nothing)
        End If

        Dim eventoClick As System.Reflection.EventInfo = tipoItem.GetEvent("Click")
        If eventoClick IsNot Nothing AndAlso manejador IsNot Nothing Then
            eventoClick.AddEventHandler(item, manejador)
        End If

        Return item
    End Function

    Private Sub AgregarElementoMenuReflexion(menu As Object, elemento As Object)
        If menu Is Nothing OrElse elemento Is Nothing Then Return

        Dim propiedadItems As System.Reflection.PropertyInfo = _
            menu.GetType().GetProperty("Items")
        If propiedadItems Is Nothing Then Throw New System.Exception( _
            "No se encontro la coleccion Items del menu contextual.")

        Dim coleccion As Object = propiedadItems.GetValue(menu, Nothing)
        If coleccion Is Nothing Then Throw New System.Exception( _
            "No se pudo obtener la coleccion Items del menu contextual.")

        For Each metodo As System.Reflection.MethodInfo In coleccion.GetType().GetMethods()
            If metodo.Name <> "Add" Then Continue For
            Dim parametros() As System.Reflection.ParameterInfo = metodo.GetParameters()
            If parametros.Length <> 1 Then Continue For
            If Not parametros(0).ParameterType.IsAssignableFrom(elemento.GetType()) Then
                Continue For
            End If

            metodo.Invoke(coleccion, New Object() {elemento})
            Return
        Next

        Throw New System.Exception("No se encontro un metodo Add compatible.")
    End Sub

    Private Sub EstablecerElementoMenuHabilitado(elemento As Object, _
            habilitado As Boolean)
        If elemento Is Nothing Then Return
        Try
            Dim propiedad As System.Reflection.PropertyInfo = _
                elemento.GetType().GetProperty("Enabled")
            If propiedad IsNot Nothing AndAlso propiedad.CanWrite Then
                propiedad.SetValue(elemento, habilitado, Nothing)
            End If
        Catch
        End Try
    End Sub

    Private Sub ActualizarEstadoMenuContextual()
        If Not _menuContextualDisponible Then Return

        Dim habilitar As Boolean = _
            Not HayIndexacionActiva() AndAlso _
            lstResultados IsNot Nothing AndAlso _
            lstResultados.Enabled AndAlso _
            lstResultados.SelectedItems.Count > 0

        EstablecerElementoMenuHabilitado(mnuCopiarRuta, habilitar)
        EstablecerElementoMenuHabilitado(mnuCopiarFichero, habilitar)
        EstablecerElementoMenuHabilitado(mnuMover, habilitar)
        EstablecerElementoMenuHabilitado(mnuBorrar, habilitar)
        EstablecerElementoMenuHabilitado(mnuAbrirCarpeta, habilitar)
        EstablecerElementoMenuHabilitado(mnuAbrir, habilitar)
    End Sub

    ' Al pulsar con el boton derecho se selecciona primero la fila situada
    ' bajo el cursor. Si ya hay una seleccion multiple y se pulsa sobre una
    ' de esas filas, se conserva toda la seleccion.
    Private Sub OnResultadosMouseDown(sender As Object, _
            e As System.Windows.Forms.MouseEventArgs)
        If e.Button <> System.Windows.Forms.MouseButtons.Right Then Return

        Dim item As System.Windows.Forms.ListViewItem = _
            lstResultados.GetItemAt(e.X, e.Y)

        If item Is Nothing Then
            For i As Integer = 0 To lstResultados.Items.Count - 1
                lstResultados.Items(i).Selected = False
            Next
            ActualizarEstadoMenuContextual()
            Return
        End If

        If Not item.Selected Then
            For i As Integer = 0 To lstResultados.Items.Count - 1
                lstResultados.Items(i).Selected = False
            Next
            item.Selected = True
        End If

        item.Focused = True
        lstResultados.Focus()
        ActualizarEstadoMenuContextual()
    End Sub

    Private Sub HabilitarAccionesResultados(habilitar As Boolean)
        If btnAbrir IsNot Nothing Then btnAbrir.Enabled = habilitar
        If btnAbrirCarpeta IsNot Nothing Then btnAbrirCarpeta.Enabled = habilitar
        If btnCopiar IsNot Nothing Then btnCopiar.Enabled = habilitar
        If btnMover IsNot Nothing Then btnMover.Enabled = habilitar
        If btnCopiarRuta IsNot Nothing Then btnCopiarRuta.Enabled = habilitar
        If btnBorrar IsNot Nothing Then btnBorrar.Enabled = habilitar
        If lstResultados IsNot Nothing Then lstResultados.Enabled = habilitar

        ActualizarEstadoMenuContextual()
    End Sub

    ' Solo el hilo que reescribe los indices. El proceso de relaciones corre
    ' aparte y no impide buscar.
    Private Function IndexandoAhora() As Boolean
        Return hiloTrabajo IsNot Nothing AndAlso hiloTrabajo.IsAlive
    End Function

    Private Function HayIndexacionActiva() As Boolean
        Return (hiloTrabajo IsNot Nothing AndAlso hiloTrabajo.IsAlive) OrElse ProcesoRelacionesActivo()
    End Function

    Private Function BloquearAccionSiIndexa() As Boolean
        If Not HayIndexacionActiva() Then Return False
        System.Windows.Forms.MessageBox.Show( _
            "Cancela o termina la indexacion antes de gestionar ficheros.", _
            "Indexacion en curso", System.Windows.Forms.MessageBoxButtons.OK, _
            System.Windows.Forms.MessageBoxIcon.Information)
        Return True
    End Function

    ' --- Ajustes (recordar rutas y opciones) ---
    Private Function ArchivoAjustes() As String
        Return System.IO.Path.Combine(CarpetaConfig(), "ajustes.txt")
    End Function

    Private Sub CargarAjustes()
        Dim ruta As String = RUTA_DEFECTO
        Dim indice As String = RUTA_INDICES
        Dim metadatos As Boolean = False
        Try
            Dim a As String = ArchivoAjustes()
            If System.IO.File.Exists(a) Then
                Dim ls() As String = System.IO.File.ReadAllLines(a)
                If ls.Length >= 1 AndAlso ls(0).Trim() <> "" Then ruta = ls(0).Trim()
                ' Conservar la ruta elegida aunque la unidad o la red no esten
                ' disponibles temporalmente al abrir el formulario.
                If ls.Length >= 2 AndAlso ls(1).Trim() <> "" Then indice = ls(1).Trim()
                If ls.Length >= 3 Then metadatos = (ls(2).Trim() = "1")
            End If
        Catch
        End Try

        txtRuta.Text = ruta
        txtIndice.Text = indice
        chkPartNumber.Checked = metadatos
        ActualizarBotonUnidad()

        _temaSeleccionado = "Oscuro"
        If cboTema IsNot Nothing Then cboTema.SelectedItem = "Oscuro"
        ActualizarPildoraSincronizado()
    End Sub

    Private Sub GuardarAjustes()
        Try
            System.IO.Directory.CreateDirectory(CarpetaConfig())
            System.IO.File.WriteAllText(ArchivoAjustes(), _
                txtRuta.Text.Trim() & vbCrLf & txtIndice.Text.Trim() & vbCrLf & _
                If(chkPartNumber.Checked, "1", "0") & vbCrLf & _
                NormalizarTema(_temaSeleccionado) & vbCrLf)
        Catch
        End Try
    End Sub

    Private Sub ActualizarPildoraSincronizado()
        If lblSincronizado Is Nothing OrElse txtRuta Is Nothing Then Return
        Dim ruta As String = txtRuta.Text.Trim()
        If ruta.Length > 24 Then ruta = ruta.Substring(0, 24) & "..."
        lblSincronizado.Text = "   " & ruta & "   ·   Indice"
    End Sub

    Private Function CarpetaIndice() As String
        Dim carpeta As String = txtIndice.Text.Trim()
        If carpeta = "" Then carpeta = RUTA_INDICES
        Return carpeta
    End Function

    Private Function Sanitizar(s As String) As String
        Dim r As String = s
        For Each c As Char In System.IO.Path.GetInvalidFileNameChars()
            r = r.Replace(c, "_"c)
        Next
        r = r.Replace(" ", "_")
        If r.Length > 80 Then r = r.Substring(0, 80)
        If r = "" Then r = "raiz"
        Return r
    End Function

    Private Function ArchivoIndiceActual() As String
        Return System.IO.Path.Combine(CarpetaIndice(), _
            "IndiceBuscador_" & Sanitizar(txtRuta.Text.Trim()) & ".txt")
    End Function

    Private Function ListarArchivosIndice() As System.Collections.Generic.List(Of String)
        Dim res As New System.Collections.Generic.List(Of String)
        Try
            Dim carpeta As String = CarpetaIndice()
            If System.IO.Directory.Exists(carpeta) Then
                For Each f As String In System.IO.Directory.GetFiles(carpeta, "IndiceBuscador_*.txt")
                    res.Add(f)
                Next
            End If
        Catch
        End Try
        Return res
    End Function

    Private Function RaizDeIndice(archivo As String) As String
        Try
            Using sr As New System.IO.StreamReader(archivo)
                Dim primera As String = sr.ReadLine()
                If primera IsNot Nothing AndAlso primera.StartsWith("#") Then
                    Dim p() As String = primera.Split(CChar(vbTab))
                    If p.Length >= 3 Then Return p(2)
                End If
            End Using
        Catch
        End Try
        Return System.IO.Path.GetFileNameWithoutExtension(archivo)
    End Function

    ' --- Eventos de rutas ---
    Private Sub OnExaminarRuta(sender As Object, e As System.EventArgs)
        Dim r As String = ElegirCarpeta(txtRuta.Text)
        If r <> "" Then
            txtRuta.Text = r
            ActualizarBotonUnidad()
            ActualizarPildoraSincronizado()
        End If
    End Sub

    Private Sub OnExaminarIndice(sender As Object, e As System.EventArgs)
        Dim r As String = ElegirCarpeta(txtIndice.Text)
        If r <> "" Then
            txtIndice.Text = r
            GuardarAjustes()
            txtCodigo.Select()
        End If
    End Sub

    Private Sub OnIndiceValidado(sender As Object, e As System.EventArgs)
        GuardarAjustes()
        If panelUsos IsNot Nothing Then panelUsos.CambiarCarpeta(CarpetaIndice())
        ActualizarInfoIndice()
    End Sub

    Private Sub OnFormularioClosing(sender As Object, e As System.Windows.Forms.FormClosingEventArgs)
        Try
            System.Windows.Forms.Application.RemoveMessageFilter(Me)
        Catch
        End Try
        cancelar = True
        LiberarRelojBusqueda()
        If panelUsos IsNot Nothing Then panelUsos.PrepararCierre()
        GuardarAjustes()
        CerrarProcesoRelaciones()
        Instancia = Nothing
    End Sub

    Private Sub OnFormularioShown(sender As Object, e As System.EventArgs)
        AplicarTemaActual()
        Me.BeginInvoke(New System.Action(AddressOf EnfocarCodigo))
    End Sub

    Private Sub OnFormularioActivated(sender As Object, e As System.EventArgs)
        ' Sin accion: la v7.6 va siempre en tema oscuro.
    End Sub

    Private Sub OnTemaChanged(sender As Object, e As System.EventArgs)
        If cboTema Is Nothing OrElse cboTema.SelectedIndex < 0 Then Return
        _temaSeleccionado = NormalizarTema(cboTema.SelectedItem.ToString())
        AplicarTemaActual()
        GuardarAjustes()
    End Sub

    Private Sub EnfocarCodigo()
        Try
            Me.ActiveControl = txtCodigo
            txtCodigo.Select()
            txtCodigo.SelectAll()
        Catch
        End Try
    End Sub

    Private Function ElegirCarpeta(inicial As String) As String
        Dim dlg As New System.Windows.Forms.FolderBrowserDialog()
        dlg.Description = "Elige la carpeta"
        Try
            If System.IO.Directory.Exists(inicial.Trim()) Then dlg.SelectedPath = inicial.Trim()
        Catch
        End Try
        If dlg.ShowDialog() = System.Windows.Forms.DialogResult.OK Then Return dlg.SelectedPath
        Return ""
    End Function

    ' Menu de unidades construido por reflexion, igual que el de resultados.
    Private Sub CrearMenuUnidades()
        menuUnidades = Nothing
        Try
            Dim ensamblado As System.Reflection.Assembly = GetType(System.Windows.Forms.Form).Assembly
            Dim tipoMenu As System.Type = ensamblado.GetType("System.Windows.Forms.ContextMenuStrip", False)
            Dim tipoItem As System.Type = ensamblado.GetType("System.Windows.Forms.ToolStripMenuItem", False)
            If tipoMenu Is Nothing OrElse tipoItem Is Nothing Then Return

            menuUnidades = System.Activator.CreateInstance(tipoMenu)
            AgregarElementoMenuReflexion(menuUnidades, CrearElementoMenuReflexion(tipoItem, _
                "Ruta de red (" & RUTA_RED & ")", New System.EventHandler(AddressOf OnUnidadElegida)))
            Try
                For Each unidad As String In System.Environment.GetLogicalDrives()
                    AgregarElementoMenuReflexion(menuUnidades, CrearElementoMenuReflexion(tipoItem, _
                        unidad, New System.EventHandler(AddressOf OnUnidadElegida)))
                Next
            Catch
            End Try
        Catch
            menuUnidades = Nothing
        End Try
    End Sub

    Private Sub OnElegirUnidad(sender As Object, e As System.EventArgs)
        If menuUnidades Is Nothing Then
            ' Sin menu disponible, el boton Examinar sigue haciendo el trabajo.
            OnExaminarRuta(sender, e)
            Return
        End If
        Try
            Dim metodo As System.Reflection.MethodInfo = menuUnidades.GetType().GetMethod( _
                "Show", New System.Type() {GetType(System.Windows.Forms.Control), _
                GetType(Integer), GetType(Integer)})
            If metodo Is Nothing Then
                OnExaminarRuta(sender, e)
                Return
            End If
            metodo.Invoke(menuUnidades, New Object() {btnUnidad, 0, btnUnidad.Height})
        Catch
            OnExaminarRuta(sender, e)
        End Try
    End Sub

    Private Sub OnUnidadElegida(sender As Object, e As System.EventArgs)
        Try
            Dim propiedad As System.Reflection.PropertyInfo = sender.GetType().GetProperty("Text")
            If propiedad Is Nothing Then Return
            Dim texto As String = System.Convert.ToString(propiedad.GetValue(sender, Nothing))
            If texto.StartsWith("Ruta de red") Then
                txtRuta.Text = RUTA_RED
            Else
                txtRuta.Text = texto
            End If
            ActualizarBotonUnidad()
            ActualizarPildoraSincronizado()
        Catch
        End Try
    End Sub

    Private Sub ActualizarBotonUnidad()
        If btnUnidad Is Nothing OrElse txtRuta Is Nothing Then Return
        Dim ruta As String = txtRuta.Text.Trim()
        If ruta.StartsWith("\\") Then
            btnUnidad.Text = "Red"
        ElseIf ruta.Length >= 2 AndAlso ruta.Substring(1, 1) = ":" Then
            btnUnidad.Text = ruta.Substring(0, 2) & "\"
        Else
            btnUnidad.Text = "Elegir..."
        End If
    End Sub

    Private Sub OnIndiceCarpetaChanged(sender As Object, e As System.EventArgs)
        cacheCarpeta = ""
    End Sub

    ' ================= TEMA VISUAL =================
    Private Function NormalizarTema(valor As String) As String
        Dim t As String = ""
        If valor IsNot Nothing Then t = valor.Trim().ToLowerInvariant()
        If t = "normal" OrElse t = "claro" Then Return "Normal"
        If t = "sistema" Then Return "Sistema"
        Return "Oscuro"
    End Function

    Private Function TemaOscuroActivo() As Boolean
        Return NormalizarTema(_temaSeleccionado) <> "Normal"
    End Function

    Private Function TipoColorSistema() As System.Type
        Try
            Dim t As System.Type = System.Type.GetType( _
                "System.Drawing.Color, System.Drawing.Primitives")
            If t Is Nothing Then
                t = System.Type.GetType("System.Drawing.Color, System.Drawing.Common")
            End If
            If t Is Nothing Then
                t = System.Type.GetType("System.Drawing.Color, System.Drawing")
            End If
            Return t
        Catch
            Return Nothing
        End Try
    End Function

    Private Function CrearColor(r As Integer, g As Integer, b As Integer) As Object
        Try
            Dim colorType As System.Type = TipoColorSistema()
            If colorType Is Nothing Then Return Nothing
            Dim tipos() As System.Type = New System.Type() { _
                GetType(Integer), GetType(Integer), GetType(Integer)}
            Dim metodo As System.Reflection.MethodInfo = colorType.GetMethod("FromArgb", tipos)
            If metodo Is Nothing Then Return Nothing
            Return metodo.Invoke(Nothing, New Object() {r, g, b})
        Catch
            Return Nothing
        End Try
    End Function

    Private Sub AsignarColor(objeto As Object, nombrePropiedad As String, color As Object)
        If objeto Is Nothing OrElse color Is Nothing Then Return
        Try
            Dim propiedad As System.Reflection.PropertyInfo = _
                objeto.GetType().GetProperty(nombrePropiedad)
            If propiedad IsNot Nothing AndAlso propiedad.CanWrite Then
                propiedad.SetValue(objeto, color, Nothing)
            End If
        Catch
        End Try
    End Sub

    Private Function CrearFuente(tamano As Single, negrita As Boolean) As Object
        Try
            Dim tipoFuente As System.Type = System.Type.GetType("System.Drawing.Font, System.Drawing.Common")
            If tipoFuente Is Nothing Then tipoFuente = System.Type.GetType("System.Drawing.Font, System.Drawing")
            If tipoFuente Is Nothing Then Return Nothing

            Dim tipoEstilo As System.Type = System.Type.GetType("System.Drawing.FontStyle, System.Drawing.Common")
            If tipoEstilo Is Nothing Then tipoEstilo = System.Type.GetType("System.Drawing.FontStyle, System.Drawing")

            If tipoEstilo IsNot Nothing Then
                Dim firma As System.Type() = New System.Type() { _
                    GetType(System.String), GetType(System.Single), tipoEstilo}
                Dim constructor As System.Reflection.ConstructorInfo = tipoFuente.GetConstructor(firma)
                If constructor IsNot Nothing Then
                    Dim estilo As Object = System.Enum.Parse(tipoEstilo, If(negrita, "Bold", "Regular"))
                    Return constructor.Invoke(New Object() {"Segoe UI", tamano, estilo})
                End If
            End If

            Dim firmaSimple As System.Type() = New System.Type() { _
                GetType(System.String), GetType(System.Single)}
            Dim constructorSimple As System.Reflection.ConstructorInfo = _
                tipoFuente.GetConstructor(firmaSimple)
            If constructorSimple Is Nothing Then Return Nothing
            Return constructorSimple.Invoke(New Object() {"Segoe UI", tamano})
        Catch
            Return Nothing
        End Try
    End Function

    Private Sub AplicarFuenteRecursiva(control As System.Windows.Forms.Control, fuente As Object)
        If control Is Nothing OrElse fuente Is Nothing Then Return
        AsignarColor(control, "Font", fuente)
        For Each hijo As System.Windows.Forms.Control In control.Controls
            AplicarFuenteRecursiva(hijo, fuente)
        Next
    End Sub

    Private Sub AplicarFuenteATenues(control As System.Windows.Forms.Control, fuente As Object)
        If control Is Nothing OrElse fuente Is Nothing Then Return
        Dim marcaControl As String = ""
        If control.Tag IsNot Nothing Then marcaControl = System.Convert.ToString(control.Tag)
        If marcaControl = "TENUE" OrElse marcaControl = "TEXTOACENTO" Then
            AsignarColor(control, "Font", fuente)
        End If
        For Each hijo As System.Windows.Forms.Control In control.Controls
            AplicarFuenteATenues(hijo, fuente)
        Next
    End Sub

    Private Sub AplicarFuentes()
        Dim base As Object = CrearFuente(CSng(9.0), False)
        If base IsNot Nothing Then AplicarFuenteRecursiva(Me, base)

        Dim pequena As Object = CrearFuente(CSng(7.5), True)
        If pequena IsNot Nothing Then AplicarFuenteATenues(Me, pequena)

        Dim titulo As Object = CrearFuente(CSng(12.0), True)
        If titulo IsNot Nothing Then AsignarColor(lblTitulo, "Font", titulo)

        Dim pestana As Object = CrearFuente(CSng(9.0), True)
        If pestana IsNot Nothing Then AsignarColor(lblPestana, "Font", pestana)

        Dim busqueda As Object = CrearFuente(CSng(12.0), False)
        If busqueda IsNot Nothing Then AsignarColor(txtCodigo, "Font", busqueda)

        Dim seleccion As Object = CrearFuente(CSng(9.5), True)
        If seleccion IsNot Nothing Then AsignarColor(lblSeleccion, "Font", seleccion)
    End Sub

    Private Sub AplicarTemaActual()
        Dim oscuro As Boolean = TemaOscuroActivo()

        If oscuro Then
            _cFondo = CrearColor(47, 58, 73)
            _cCabecera = CrearColor(38, 47, 60)
            _cTarjeta = CrearColor(54, 65, 82)
            _cAcciones = CrearColor(58, 69, 86)
            _cEntrada = CrearColor(42, 52, 66)
            _cLista = CrearColor(38, 48, 61)
            _cBoton = CrearColor(67, 79, 97)
            _cTexto = CrearColor(235, 238, 242)
            _cTenue = CrearColor(150, 163, 180)
            _cBorde = CrearColor(91, 107, 128)
            _cAcento = CrearColor(214, 158, 46)
            _cTextoAcento = CrearColor(30, 35, 44)
            _cCerrar = CrearColor(158, 63, 63)
        Else
            _cFondo = CrearColor(245, 246, 248)
            _cCabecera = CrearColor(232, 235, 240)
            _cTarjeta = CrearColor(255, 255, 255)
            _cAcciones = CrearColor(238, 240, 244)
            _cEntrada = CrearColor(255, 255, 255)
            _cLista = CrearColor(255, 255, 255)
            _cBoton = CrearColor(236, 238, 242)
            _cTexto = CrearColor(28, 28, 30)
            _cTenue = CrearColor(110, 120, 134)
            _cBorde = CrearColor(176, 181, 188)
            _cAcento = CrearColor(214, 158, 46)
            _cTextoAcento = CrearColor(30, 35, 44)
            _cCerrar = CrearColor(200, 90, 90)
        End If

        If _cFondo Is Nothing Then Return

        AsignarColor(Me, "BackColor", _cFondo)
        AsignarColor(Me, "ForeColor", _cTexto)

        For Each control As System.Windows.Forms.Control In Me.Controls
            AplicarTemaAControl(Control, oscuro)
        Next

        AplicarEstiloFilas()
        AplicarTemaMenuContextual(oscuro, _cEntrada, _cTexto)
        AplicarFuentes()

        ' No usar Invalidate(Boolean): en el compilador iLogic de Inventor 2026
        ' esa sobrecarga fuerza referencias a System.Drawing.Common/Primitives.
        Try
            Me.Refresh()
        Catch
        End Try
    End Sub

    ' Devuelve el fondo del contenedor al que pertenece un control, para que las
    ' etiquetas no se recorten sobre un color distinto al de su tarjeta.
    Private Function FondoDeContenedor(control As System.Windows.Forms.Control) As Object
        Dim padre As System.Windows.Forms.Control = control.Parent
        While padre IsNot Nothing
            ' La marca se mira antes que el tipo: una cabecera dentro del panel
            ' de usos debe salir ambar, no del color de la tarjeta.
            Dim marca As String = ""
            If padre.Tag IsNot Nothing Then marca = System.Convert.ToString(padre.Tag)
            If marca = "CABTABLA" Then Return _cAcento
            If TypeOf padre Is ConsultaUsosPanel Then Return _cTarjeta
            If marca = "CAMPO" Then Return _cEntrada
            If marca = "CABECERA" OrElse marca = "ESTADO" Then Return _cCabecera
            If marca = "ACCIONES" Then Return _cAcciones
            If marca = "TARJETA" OrElse marca = "BUSQUEDA" Then Return _cTarjeta
            padre = padre.Parent
        End While
        Return _cFondo
    End Function

    Private Sub AplicarTemaMenuContextual(oscuro As Boolean, _
            fondo As Object, texto As Object)
        If Not _menuContextualDisponible OrElse menuResultados Is Nothing Then Return

        AsignarColor(menuResultados, "BackColor", fondo)
        AsignarColor(menuResultados, "ForeColor", texto)
        AsignarColor(menuUnidades, "BackColor", fondo)
        AsignarColor(menuUnidades, "ForeColor", texto)

        Dim elementos() As Object = New Object() { _
            mnuCopiarRuta, mnuCopiarFichero, mnuMover, mnuBorrar, _
            mnuAbrirCarpeta, mnuAbrir}

        For Each elemento As Object In elementos
            AsignarColor(elemento, "BackColor", fondo)
            AsignarColor(elemento, "ForeColor", texto)
        Next
    End Sub

    Private Sub AplicarTemaAControl(control As System.Windows.Forms.Control, oscuro As Boolean)
        If control Is Nothing Then Return

        Dim marca As String = ""
        If control.Tag IsNot Nothing Then marca = System.Convert.ToString(control.Tag)

        If TypeOf control Is System.Windows.Forms.TextBox Then
            Dim caja As System.Windows.Forms.TextBox = _
                DirectCast(control, System.Windows.Forms.TextBox)
            ' El borde lo quita CampoTexto al construirlo. Aqui solo el color, y
            ' el mismo que el del marco para que se vea una caja continua.
            AsignarColor(caja, "BackColor", _cEntrada)
            AsignarColor(caja, "ForeColor", _cTexto)

        ElseIf TypeOf control Is System.Windows.Forms.ComboBox Then
            Dim combo As System.Windows.Forms.ComboBox = _
                DirectCast(control, System.Windows.Forms.ComboBox)
            combo.FlatStyle = System.Windows.Forms.FlatStyle.Flat
            AsignarColor(combo, "BackColor", _cEntrada)
            AsignarColor(combo, "ForeColor", _cTexto)

        ElseIf TypeOf control Is System.Windows.Forms.ListView Then
            Dim lista As System.Windows.Forms.ListView = _
                DirectCast(control, System.Windows.Forms.ListView)
            lista.BorderStyle = System.Windows.Forms.BorderStyle.None
            AsignarColor(lista, "BackColor", _cLista)
            AsignarColor(lista, "ForeColor", _cTexto)

        ElseIf TypeOf control Is System.Windows.Forms.Button Then
            Dim pulsador As System.Windows.Forms.Button = _
                DirectCast(control, System.Windows.Forms.Button)
            pulsador.UseVisualStyleBackColor = False
            pulsador.FlatStyle = System.Windows.Forms.FlatStyle.Flat
            pulsador.FlatAppearance.BorderSize = 1

            If marca = "ACENTO" Then
                AsignarColor(pulsador, "BackColor", _cAcento)
                AsignarColor(pulsador, "ForeColor", _cTextoAcento)
                AsignarColor(pulsador.FlatAppearance, "BorderColor", _cAcento)
                AsignarColor(pulsador.FlatAppearance, "MouseOverBackColor", CrearColor(232, 178, 70))
            Else
                AsignarColor(pulsador, "BackColor", _cBoton)
                AsignarColor(pulsador, "ForeColor", _cTexto)
                AsignarColor(pulsador.FlatAppearance, "BorderColor", _cBorde)
                If marca = "CERRAR" Then
                    AsignarColor(pulsador.FlatAppearance, "MouseOverBackColor", _cCerrar)
                ElseIf oscuro Then
                    AsignarColor(pulsador.FlatAppearance, "MouseOverBackColor", CrearColor(67, 91, 113))
                    AsignarColor(pulsador.FlatAppearance, "MouseDownBackColor", CrearColor(51, 110, 144))
                End If
            End If

        ElseIf TypeOf control Is System.Windows.Forms.Label _
                OrElse TypeOf control Is System.Windows.Forms.RadioButton _
                OrElse TypeOf control Is System.Windows.Forms.CheckBox Then
            If marca = "PILDORA" Then
                AsignarColor(control, "BackColor", _cEntrada)
                AsignarColor(control, "ForeColor", _cTenue)
            ElseIf marca = "TEXTOACENTO" Then
                AsignarColor(control, "BackColor", _cAcento)
                AsignarColor(control, "ForeColor", _cTextoAcento)
            Else
                AsignarColor(control, "BackColor", FondoDeContenedor(control))
                AsignarColor(control, "ForeColor", If(marca = "TENUE", _cTenue, _cTexto))
            End If

        ElseIf TypeOf control Is System.Windows.Forms.ProgressBar Then
            AsignarColor(control, "BackColor", _cEntrada)
            AsignarColor(control, "ForeColor", _cAcento)

        ElseIf TypeOf control Is ConsultaUsosPanel Then
            AsignarColor(control, "BackColor", _cTarjeta)
            AsignarColor(control, "ForeColor", _cTexto)

        ElseIf TypeOf control Is System.Windows.Forms.Panel Then
            Dim fondo As Object = _cTarjeta
            If marca = "CABTABLA" Then fondo = _cAcento
            If marca = "CAMPO" Then fondo = _cEntrada
            If marca = "CABECERA" OrElse marca = "ESTADO" Then fondo = _cCabecera
            If marca = "ACCIONES" Then fondo = _cAcciones
            AsignarColor(control, "BackColor", fondo)
            AsignarColor(control, "ForeColor", _cTexto)

        Else
            AsignarColor(control, "BackColor", _cFondo)
            AsignarColor(control, "ForeColor", _cTexto)
        End If

        If control.HasChildren Then
            For Each hijo As System.Windows.Forms.Control In control.Controls
                AplicarTemaAControl(hijo, oscuro)
            Next
        End If
    End Sub

    ' ================= INDEXACION =================
    Private Sub OnIndexar(sender As Object, e As System.EventArgs)
        EjecutarIndexacion(False)
    End Sub

    Private Sub OnActualizar(sender As Object, e As System.EventArgs)
        EjecutarIndexacion(True)
    End Sub

    Private Sub EjecutarIndexacion(esActualizacion As Boolean)
        If HayIndexacionActiva() Then Return

        Dim ruta As String = txtRuta.Text.Trim()
        If ruta = "" Then
            lblEstado.Text = "Selecciona la carpeta a indexar."
            Return
        End If

        GuardarAjustes()
        cancelar = False

        If chkPartNumber.Checked Then
            Me.Cursor = System.Windows.Forms.Cursors.WaitCursor
            lblEstado.Text = "Comprobando cuantos ficheros hay que abrir..."
            lblEstado.Refresh()
            Dim pendientes As Integer = ContarFicherosSinPropiedades(ruta, ArchivoIndiceActual())
            Me.Cursor = System.Windows.Forms.Cursors.Default
            If pendientes < 0 Then
                lblEstado.Text = "No se pudo acceder a la carpeta a indexar."
                Return
            End If
            If pendientes > 0 Then
                Dim resp As System.Windows.Forms.DialogResult = System.Windows.Forms.MessageBox.Show( _
                    "Hay que abrir " & pendientes.ToString() & " fichero(s) en Inventor para leer " & _
                    "Nº de pieza y descripcion." & vbCrLf & vbCrLf & _
                    "Inventor se quedara ocupado mientras dure y en una carpeta grande puede " & _
                    "tardar mucho. Puedes detenerlo con Cancelar en cualquier momento." & vbCrLf & vbCrLf & _
                    "¿Continuar?", "Leer propiedades", _
                    System.Windows.Forms.MessageBoxButtons.YesNo, _
                    System.Windows.Forms.MessageBoxIcon.Warning, _
                    System.Windows.Forms.MessageBoxDefaultButton.Button2)
                If resp <> System.Windows.Forms.DialogResult.Yes Then
                    lblEstado.Text = "Indexado cancelado."
                    Return
                End If
            End If
        End If

        btnIndexar.Enabled = False
        btnActualizar.Enabled = False
        btnBuscar.Enabled = True
        btnCancelar.Enabled = True
        HabilitarAccionesResultados(False)
        barraProgreso.Style = System.Windows.Forms.ProgressBarStyle.Blocks
        barraProgreso.Minimum = 0 : barraProgreso.Maximum = 100 : barraProgreso.Value = 0
        barraProgreso.Visible = True
        lblPorcentaje.Text = "0 %" : lblPorcentaje.Visible = True

        Dim archivo As String = ArchivoIndiceActual()
        _archivoIndexadoEnCurso = archivo
        _avisosPropiedades = 0
        Dim modo As String = If(esActualizacion, "Actualizando", "Indexando")

        Dim conPropiedades As Boolean = chkPartNumber.Checked
        If conPropiedades Then
            lblEstado.Text = modo & " con propiedades: " & ruta & " ..."
            hiloTrabajo = New System.Threading.Thread(Sub() EjecutarIndexadoCompleto(ruta, archivo, esActualizacion))
        Else
            lblEstado.Text = modo & " nombres de archivos en segundo plano: " & ruta & " ..."
            hiloTrabajo = New System.Threading.Thread(Sub() EjecutarIndexadoRapido(ruta, archivo, esActualizacion))
        End If
        hiloTrabajo.IsBackground = True
        Try
            hiloTrabajo.SetApartmentState(System.Threading.ApartmentState.STA)
        Catch
        End Try
        hiloTrabajo.Start()
    End Sub

    ' Al marcar la casilla se avisa una vez de lo que implica, para que nadie
    ' lance por error un indexado de horas.
    Private Sub OnMetadatosChanged(sender As Object, e As System.EventArgs)
        GuardarAjustes()
        If chkPartNumber.Checked Then
            lblEstado.Text = "Reindexar leera Nº de pieza y descripcion. Abre cada fichero en Inventor: es lento y solo se abren los modificados."
        Else
            lblEstado.Text = "Indexado rapido: solo nombre y fecha. No abre nada en Inventor."
        End If
    End Sub

    ' Cuenta cuantos ficheros habria que abrir de verdad. Los que conserven la
    ' fecha del indice anterior se copian y no se abren.
    Private Function ContarFicherosSinPropiedades(ruta As String, archivo As String) As Integer
        Dim pendientes As Integer = 0
        Try
            Dim viejo As System.Collections.Generic.Dictionary(Of String, String()) = _
                CargarIndiceDiccionario(archivo)
            Dim lista As New System.Collections.Generic.List(Of String)
            ReunirArchivosIndexables(ruta, lista)
            For Each f As String In lista
                Dim ticks As Long = 0
                Try
                    ticks = System.IO.File.GetLastWriteTime(f).Ticks
                Catch
                End Try
                Dim prev() As String = Nothing
                If viejo.TryGetValue(f, prev) AndAlso prev(0) = ticks.ToString() AndAlso _
                        (prev(1) <> "" OrElse prev(2) <> "") Then Continue For
                pendientes += 1
            Next
        Catch
            Return -1
        End Try
        Return pendientes
    End Function

    Private Function CargarIndiceDiccionario(archivo As String) _
            As System.Collections.Generic.Dictionary(Of String, String())
        Dim d As New System.Collections.Generic.Dictionary(Of String, String())( _
            System.StringComparer.OrdinalIgnoreCase)
        Try
            If System.IO.File.Exists(archivo) Then
                For Each l As String In System.IO.File.ReadAllLines(archivo)
                    If l = "" OrElse l.StartsWith("#") Then Continue For
                    Dim p() As String = l.Split(CChar(vbTab))
                    If p.Length < 2 Then Continue For
                    Dim pn As String = ""
                    Dim desc As String = ""
                    If p.Length >= 3 Then pn = p(2)
                    If p.Length >= 4 Then desc = p(3)
                    d(p(0)) = New String() {p(1), pn, desc}
                Next
            End If
        Catch
        End Try
        Return d
    End Function

    Private Sub EscribirEntrada(sw As System.IO.StreamWriter, ruta As String, _
            ticks As Long, pn As String, desc As String)
        Dim ext As String = System.IO.Path.GetExtension(ruta).ToLower()
        If ext = ".ipt" Then
            _nPiezas += 1
        ElseIf ext = ".iam" Then
            _nEnsam += 1
        ElseIf ext = ".idw" Then
            _nPlanos += 1
        End If
        Dim pnLimpio As String = pn.Replace(vbTab, " ").Replace(vbCr, " ").Replace(vbLf, " ")
        Dim descLimpio As String = desc.Replace(vbTab, " ").Replace(vbCr, " ").Replace(vbLf, " ")
        sw.WriteLine(ruta & vbTab & ticks.ToString() & vbTab & pnLimpio & vbTab & descLimpio)
    End Sub

    Private Sub EjecutarIndexadoRapido(ruta As String, archivo As String, esActualizacion As Boolean)
        _cuentaIndexada = 0
        _progreso = 0
        _totalIndexar = 0
        _leidosDeInventor = 0
        _reutilizados = 0
        _faseIndexacion = "Contando"
        _nPiezas = 0
        _nEnsam = 0
        _nPlanos = 0
        _errorTrabajo = ""

        Dim viejo As System.Collections.Generic.Dictionary(Of String, String()) = _
            CargarIndiceDiccionario(archivo)
        Dim archivoTemporal As String = archivo & ".tmp"

        Try
            System.IO.Directory.CreateDirectory(System.IO.Path.GetDirectoryName(archivo))
            If Not System.IO.Directory.Exists(ruta) Then Throw New System.Exception("No se puede acceder a la carpeta a indexar.")
            If System.IO.File.Exists(archivoTemporal) Then System.IO.File.Delete(archivoTemporal)

            Dim archivosIndexables As New System.Collections.Generic.List(Of String)
            _faseIndexacion = "Contando"
            _progreso = 0 : _totalIndexar = 0
            ActualizarProgresoAsync()
            ReunirArchivosIndexables(ruta, archivosIndexables)
            _totalIndexar = archivosIndexables.Count
            _progreso = 0 : _faseIndexacion = "Indexando"
            ActualizarProgresoAsync()

            Using sw As New System.IO.StreamWriter(archivoTemporal, False, New System.Text.UTF8Encoding(False))
                sw.WriteLine("#INDICE" & vbTab & System.DateTime.Now.ToString("yyyy-MM-dd HH:mm") & vbTab & ruta)
                _cuentaIndexada = IndexarListaRapido(archivosIndexables, sw, viejo)
            End Using

            If cancelar Then
                Try
                    If System.IO.File.Exists(archivoTemporal) Then System.IO.File.Delete(archivoTemporal)
                Catch
                End Try
            Else
                ReemplazarIndiceDeFormaSegura(archivoTemporal, archivo)
            End If

        Catch ex As System.Exception
            _errorTrabajo = ex.Message
            Try
                If System.IO.File.Exists(archivoTemporal) Then System.IO.File.Delete(archivoTemporal)
            Catch
            End Try
        End Try

        ' El vaciado de las cacheras se hace en FinIndexado, que corre en el hilo
        ' de la interfaz. Hacerlo aqui puede dejar a media lectura al hilo que
        ' dibuja los resultados.
        Try
            If Me.IsHandleCreated AndAlso Not Me.IsDisposed Then
                Me.BeginInvoke(New System.Action(AddressOf FinIndexado))
            End If
        Catch
        End Try
    End Sub

    Private Sub ReunirArchivosIndexables(carpeta As String, archivos As System.Collections.Generic.List(Of String))
        If cancelar Then Return
        Dim ficheros() As String = Nothing
        Try
            ficheros = System.IO.Directory.GetFiles(carpeta)
        Catch
            Return
        End Try
        For Each f As String In ficheros
            If cancelar Then Return
            If EsIndexable(System.IO.Path.GetExtension(f).ToLowerInvariant()) Then
                archivos.Add(f)
                _progreso = archivos.Count
                If (_progreso Mod 200) = 0 Then ActualizarProgresoAsync()
            End If
        Next
        Dim subs() As String = Nothing
        Try
            subs = System.IO.Directory.GetDirectories(carpeta)
        Catch
            Return
        End Try
        For Each sc As String In subs
            If cancelar Then Return
            If EsCarpetaExcluida(sc) Then Continue For
            ReunirArchivosIndexables(sc, archivos)
        Next
    End Sub

    Private Function IndexarListaRapido(archivos As System.Collections.Generic.List(Of String), _
            sw As System.IO.StreamWriter, viejo As System.Collections.Generic.Dictionary(Of String, String())) As Integer
        Dim n As Integer = 0
        For Each f As String In archivos
            If cancelar Then Return n
            Dim ticks As Long = 0
            Try
                ticks = System.IO.File.GetLastWriteTime(f).Ticks
            Catch
            End Try
            Dim pn As String = ""
            Dim desc As String = ""
            Dim prev() As String = Nothing
            If viejo.TryGetValue(f, prev) AndAlso prev(0) = ticks.ToString() Then
                pn = prev(1)
                desc = prev(2)
            End If
            EscribirEntrada(sw, f, ticks, pn, desc)
            n += 1
            _progreso = n
            If (_progreso Mod 50) = 0 OrElse _progreso = _totalIndexar Then ActualizarProgresoAsync()
        Next
        Return n
    End Function

    ' Igual que el rapido, pero abriendo en Inventor los ficheros cuyo Nº de
    ' pieza y descripcion no esten ya en el indice anterior con la misma fecha.
    Private Sub EjecutarIndexadoCompleto(ruta As String, archivo As String, esActualizacion As Boolean)
        _cuentaIndexada = 0
        _progreso = 0
        _totalIndexar = 0
        _leidosDeInventor = 0
        _reutilizados = 0
        _faseIndexacion = "Contando"
        _nPiezas = 0
        _nEnsam = 0
        _nPlanos = 0
        _errorTrabajo = ""

        Dim viejo As System.Collections.Generic.Dictionary(Of String, String()) = _
            CargarIndiceDiccionario(archivo)
        Dim archivoTemporal As String = archivo & ".tmp"

        Try
            System.IO.Directory.CreateDirectory(System.IO.Path.GetDirectoryName(archivo))
            If Not System.IO.Directory.Exists(ruta) Then Throw New System.Exception("No se puede acceder a la carpeta a indexar.")
            If System.IO.File.Exists(archivoTemporal) Then System.IO.File.Delete(archivoTemporal)

            Dim archivosIndexables As New System.Collections.Generic.List(Of String)
            ActualizarProgresoAsync()
            ReunirArchivosIndexables(ruta, archivosIndexables)
            _totalIndexar = archivosIndexables.Count
            _progreso = 0 : _faseIndexacion = "Propiedades"
            ActualizarProgresoAsync()

            Using sw As New System.IO.StreamWriter(archivoTemporal, False, New System.Text.UTF8Encoding(False))
                sw.WriteLine("#INDICE" & vbTab & System.DateTime.Now.ToString("yyyy-MM-dd HH:mm") & vbTab & ruta & vbTab & "PN+DESC")
                _cuentaIndexada = IndexarListaCompleto(archivosIndexables, sw, viejo)
            End Using

            If cancelar Then
                Try
                    If System.IO.File.Exists(archivoTemporal) Then System.IO.File.Delete(archivoTemporal)
                Catch
                End Try
            Else
                ReemplazarIndiceDeFormaSegura(archivoTemporal, archivo)
            End If

        Catch ex As System.Exception
            _errorTrabajo = ex.Message
            Try
                If System.IO.File.Exists(archivoTemporal) Then System.IO.File.Delete(archivoTemporal)
            Catch
            End Try
        End Try

        Try
            If Me.IsHandleCreated AndAlso Not Me.IsDisposed Then
                Me.BeginInvoke(New System.Action(AddressOf FinIndexado))
            End If
        Catch
        End Try
    End Sub

    Private Function IndexarListaCompleto(archivos As System.Collections.Generic.List(Of String), _
            sw As System.IO.StreamWriter, viejo As System.Collections.Generic.Dictionary(Of String, String())) As Integer
        Dim n As Integer = 0
        For Each f As String In archivos
            If cancelar Then Return n
            Dim ticks As Long = 0
            Try
                ticks = System.IO.File.GetLastWriteTime(f).Ticks
            Catch
            End Try

            Dim pn As String = ""
            Dim desc As String = ""
            Dim prev() As String = Nothing
            If viejo.TryGetValue(f, prev) AndAlso prev(0) = ticks.ToString() AndAlso _
                    (prev(1) <> "" OrElse prev(2) <> "") Then
                ' Ya se leyo en su dia y el fichero no ha cambiado: no se abre.
                pn = prev(1)
                desc = prev(2)
                _reutilizados += 1
            Else
                Dim datos() As String = LeerPropiedadesPieza(f)
                pn = datos(0)
                desc = datos(1)
                _leidosDeInventor += 1
            End If

            EscribirEntrada(sw, f, ticks, pn, desc)
            n += 1
            _progreso = n
            ActualizarProgresoAsync()
        Next
        Return n
    End Function

    ' La API de Inventor es de un solo hilo: el trabajo vuelve al hilo de la
    ' interfaz. Un fichero que falle suma un aviso pero no detiene el indexado.
    Private Function LeerPropiedadesPieza(ruta As String) As String()
        Try
            Dim datos As System.Collections.Generic.List(Of String()) = DirectCast( _
                Me.Invoke(New System.Func(Of System.Collections.Generic.List(Of String()))( _
                    Function() LeerDocumentoParaIndice(ruta, True))), _
                System.Collections.Generic.List(Of String()))
            If datos Is Nothing OrElse datos.Count = 0 Then Return New String() {"", ""}
            Return datos(0)
        Catch ex As System.Exception
            System.Threading.Interlocked.Increment(_avisosPropiedades)
            Return New String() {"", ""}
        End Try
    End Function

    Private Sub ActualizarProgresoAsync()
        Try
            If Me.IsHandleCreated AndAlso Not Me.IsDisposed Then
                Me.BeginInvoke(New System.Action(AddressOf MostrarProgreso))
            End If
        Catch
        End Try
    End Sub

    Private Sub MostrarProgreso()
        If barraProgreso Is Nothing OrElse lblPorcentaje Is Nothing Then Return
        barraProgreso.Minimum = 0 : barraProgreso.Maximum = 100
        barraProgreso.Visible = True : lblPorcentaje.Visible = True
        If _faseIndexacion = "Contando" Then
            barraProgreso.Style = System.Windows.Forms.ProgressBarStyle.Marquee
            barraProgreso.MarqueeAnimationSpeed = 30
            lblPorcentaje.Text = "..."
            lblEstado.Text = "Contando archivos... " & _progreso.ToString() & " encontrados."
        Else
            barraProgreso.Style = System.Windows.Forms.ProgressBarStyle.Blocks
            barraProgreso.MarqueeAnimationSpeed = 0
            Dim porcentaje As Integer = 100
            If _totalIndexar > 0 Then
                porcentaje = System.Math.Min(100, CInt(System.Math.Floor(CDbl(_progreso) * 100.0 / CDbl(_totalIndexar))))
            End If
            barraProgreso.Value = porcentaje
            lblPorcentaje.Text = porcentaje.ToString() & " %"
            If _faseIndexacion = "Propiedades" Then
                lblEstado.Text = "Leyendo propiedades: " & porcentaje.ToString() & " % (" & _
                    _progreso.ToString() & " de " & _totalIndexar.ToString() & " archivos; " & _
                    _leidosDeInventor.ToString() & " abiertos, " & _reutilizados.ToString() & " ya en cache)."
            Else
                lblEstado.Text = "Indexando: " & porcentaje.ToString() & " % (" & _progreso.ToString() & " de " & _totalIndexar.ToString() & " archivos)."
            End If
        End If
    End Sub

    ' Lectura de iProperties. Hoy no se usa porque el indexado completo esta
    ' desactivado, pero se conserva por si se vuelve a habilitar el checkbox.
    Private Function LeerDocumentoParaIndice(ruta As String, propiedades As Boolean) As System.Collections.Generic.List(Of String())
        Dim salida As New System.Collections.Generic.List(Of String())
        Dim doc As Inventor.Document = Nothing
        Dim propio As Boolean = False
        Dim silencio As Boolean = oApp.SilentOperation
        Try
            For Each abierto As Inventor.Document In oApp.Documents
                If String.Equals(abierto.FullFileName, ruta, System.StringComparison.OrdinalIgnoreCase) Then
                    doc = abierto : Exit For
                End If
            Next
            If doc Is Nothing Then
                oApp.SilentOperation = True
                doc = oApp.Documents.Open(ruta, False)
                propio = True
            ElseIf doc.Dirty Then
                Throw New System.Exception("Tiene cambios sin guardar; guarda el documento y vuelve a actualizar el indice.")
            End If
            If propiedades Then
                Dim pn As String = System.Convert.ToString(doc.PropertySets.Item("Design Tracking Properties").Item("Part Number").Value)
                Dim descripcion As String = System.Convert.ToString(doc.PropertySets.Item("Design Tracking Properties").Item("Description").Value)
                salida.Add(New String() {pn, descripcion})
            Else
                For Each referencia As Inventor.FileDescriptor In doc.File.ReferencedFileDescriptors
                    Dim hijo As String = referencia.FullFileName
                    Dim ext As String = System.IO.Path.GetExtension(hijo).ToLowerInvariant()
                    If ext <> ".ipt" AndAlso ext <> ".iam" Then Continue For
                    If referencia.ReferenceMissing OrElse referencia.ReferenceInternalNameDifferent Then
                        salida.Add(New String() {hijo, "Referencia no resuelta o identidad distinta"})
                    Else
                        salida.Add(New String() {hijo, ""})
                    End If
                Next
            End If
        Finally
            Try
                If propio AndAlso doc IsNot Nothing Then doc.Close(True)
            Finally
                oApp.SilentOperation = silencio
            End Try
        End Try
        Return salida
    End Function

    Private Sub FinIndexado()
        _indice = Nothing
        _indiceFirma = ""
        _resultadosBusqueda = Nothing
        _codigoBusquedaActual = ""
        cacheCarpeta = ""

        btnBuscar.Enabled = True
        HabilitarAccionesResultados(True)
        ActualizarInfoIndice()

        If _errorTrabajo <> "" Then
            btnIndexar.Enabled = True : btnActualizar.Enabled = True : btnCancelar.Enabled = False
            lblEstado.Text = "Error al indexar: " & _errorTrabajo
            barraProgreso.Visible = False : lblPorcentaje.Visible = False
        ElseIf cancelar Then
            btnIndexar.Enabled = True : btnActualizar.Enabled = True : btnCancelar.Enabled = False
            lblEstado.Text = "Indexacion cancelada (" & _cuentaIndexada.ToString() & " ficheros)."
            barraProgreso.Visible = False : lblPorcentaje.Visible = False
        Else
            barraProgreso.Maximum = 100 : barraProgreso.Value = 100
            lblPorcentaje.Text = "100 %" : lblPorcentaje.Visible = True
            Dim resumen As String = "Indice creado: " & _cuentaIndexada.ToString() & " ficheros (" & _
                _nPiezas.ToString() & " piezas, " & _nEnsam.ToString() & " ensamblajes, " & _
                _nPlanos.ToString() & " planos)."
            If _leidosDeInventor > 0 OrElse _reutilizados > 0 Then
                resumen &= " Propiedades: " & _leidosDeInventor.ToString() & " leidas, " & _
                    _reutilizados.ToString() & " reutilizadas"
                If _avisosPropiedades > 0 Then resumen &= ", " & _avisosPropiedades.ToString() & " con aviso"
                resumen &= "."
            End If
            lblEstado.Text = resumen & " Preparando relaciones..."
            If panelUsos IsNot Nothing Then panelUsos.CambiarCarpeta(CarpetaIndice(), True)
            LanzarRelacionesEnSegundoInventor()
        End If
    End Sub

    ' ================= BUSQUEDA (sobre el indice) =================
    Private Function ExtensionesActivas() As System.Collections.Generic.List(Of String)
        Dim exts As New System.Collections.Generic.List(Of String)
        If rdoPiezas.Checked Then
            exts.Add(".ipt")
        ElseIf rdoEnsamblajes.Checked Then
            exts.Add(".iam")
        ElseIf rdoPlanos.Checked Then
            exts.Add(".idw")
        Else
            exts.Add(".ipt")
            exts.Add(".iam")
            exts.Add(".idw")
        End If
        Return exts
    End Function

    Private Function EsIndexable(ext As String) As Boolean
        Return ext = ".ipt" OrElse ext = ".iam" OrElse ext = ".idw"
    End Function

    Private Function EsCarpetaExcluida(carpeta As String) As Boolean
        Dim nombre As String = System.IO.Path.GetFileName(carpeta.TrimEnd("\"c))
        Return String.Equals(nombre, "OldVersions", System.StringComparison.OrdinalIgnoreCase)
    End Function

    Private Function EsCopiaSeguridad(ruta As String) As Boolean
        Return ruta.ToLower().Contains("\oldversions\")
    End Function

    Private Function FirmaIndices(archivos As System.Collections.Generic.List(Of String)) As String
        Dim sb As New System.Text.StringBuilder()
        For Each a As String In archivos
            sb.Append(a).Append("|")
            Try
                sb.Append(System.IO.File.GetLastWriteTime(a).Ticks)
            Catch
            End Try
            sb.Append(";")
        Next
        Return sb.ToString()
    End Function

    Private Function LeerLineasIndiceConReintento(archivo As String, _
                                                   intentos As Integer, _
                                                   esperaMs As Integer) As String()
        Dim ultimoError As System.Exception = Nothing

        For i As Integer = 1 To intentos
            Try
                Using fs As New System.IO.FileStream(archivo, _
                                                    System.IO.FileMode.Open, _
                                                    System.IO.FileAccess.Read, _
                                                    System.IO.FileShare.ReadWrite)
                    Using sr As New System.IO.StreamReader(fs, System.Text.Encoding.UTF8, True)
                        Dim contenido As String = sr.ReadToEnd()
                        Return contenido.Replace(vbCrLf, vbLf).Replace(vbCr, vbLf).Split(CChar(vbLf))
                    End Using
                End Using
            Catch ex As System.Exception
                ultimoError = ex
                System.Threading.Thread.Sleep(esperaMs)
            End Try
        Next

        If ultimoError IsNot Nothing Then Throw ultimoError
        Return New String() {}
    End Function

    Private Sub ReemplazarIndiceDeFormaSegura(archivoTemporal As String, archivoFinal As String)
        Dim carpeta As String = System.IO.Path.GetDirectoryName(archivoFinal)
        If carpeta <> "" AndAlso Not System.IO.Directory.Exists(carpeta) Then
            System.IO.Directory.CreateDirectory(carpeta)
        End If

        Dim copiaSeguridad As String = archivoFinal & ".bak"
        If System.IO.File.Exists(copiaSeguridad) Then
            Try
                System.IO.File.Delete(copiaSeguridad)
            Catch
            End Try
        End If

        If Not System.IO.File.Exists(archivoFinal) Then
            System.IO.File.Move(archivoTemporal, archivoFinal)
            Return
        End If

        Try
            ' File.Replace es atomico cuando el sistema de archivos y la red lo admiten.
            System.IO.File.Replace(archivoTemporal, archivoFinal, copiaSeguridad, True)
        Catch
            ' Alternativa segura para unidades de red que no admiten File.Replace.
            System.IO.File.Copy(archivoFinal, copiaSeguridad, True)
            Try
                System.IO.File.Copy(archivoTemporal, archivoFinal, True)
                System.IO.File.Delete(archivoTemporal)
            Catch
                Try
                    If System.IO.File.Exists(copiaSeguridad) Then
                        System.IO.File.Copy(copiaSeguridad, archivoFinal, True)
                    End If
                Catch
                End Try
                Throw
            End Try
        End Try

        Try
            If System.IO.File.Exists(copiaSeguridad) Then System.IO.File.Delete(copiaSeguridad)
        Catch
        End Try
    End Sub

    Private Class ResultadoCarga
        Public Indice As System.Collections.Generic.List(Of String())
        Public Coincidencias As System.Collections.Generic.List(Of String())
        Public Carpeta As String
        Public Codigo As String
        Public ErrorLectura As String = ""
        Public Avisos As Integer
        Public Archivos As Integer
        Public Version As Integer
        Public Truncado As Boolean
    End Class

    Private relojDatos As System.Windows.Forms.Timer
    Private datosPendientes As Boolean
    Private leyendoDatos As Boolean
    Private codigoPendiente As String = ""
    Private carpetaPendiente As String = ""
    Private versionDatos As Integer
    Private cacheCarpeta As String = ""
    Private cacheArchivos As Integer
    Private cacheAvisos As Integer
    Private resultadoDatos As ResultadoCarga
    Private cerradoDatos As Boolean
    Private ReadOnly bloqueoDatos As New Object()

    Private Sub PedirDatos(codigo As String, Optional recargar As Boolean = False)
        If cerradoDatos Then Return
        carpetaPendiente = CarpetaIndice()
        codigoPendiente = codigo
        versionDatos += 1
        If recargar Then cacheCarpeta = ""
        datosPendientes = True
        If relojDatos Is Nothing Then
            relojDatos = New System.Windows.Forms.Timer()
            relojDatos.Interval = 100
            AddHandler relojDatos.Tick, AddressOf ProcesarDatos
            AddHandler Me.Disposed, AddressOf CerrarDatos
            relojDatos.Start()
        End If
        lblIndiceInfo.Text = "Cargando indices..."
        If codigo <> "" Then lblEstado.Text = "Buscando " & codigo & "..."
    End Sub

    Private Sub CerrarDatos(sender As Object, e As System.EventArgs)
        SyncLock bloqueoDatos
            cerradoDatos = True
            cancelar = True
        End SyncLock
        If relojDatos IsNot Nothing Then relojDatos.Stop() : relojDatos.Dispose()
    End Sub

    Private Sub ProcesarDatos(sender As Object, e As System.EventArgs)
        Dim recibido As ResultadoCarga = Nothing
        SyncLock bloqueoDatos
            recibido = resultadoDatos
            resultadoDatos = Nothing
        End SyncLock
        If recibido IsNot Nothing AndAlso recibido.Version = versionDatos Then
            If recibido.Indice IsNot Nothing Then
                _indice = recibido.Indice
                cacheCarpeta = recibido.Carpeta
                cacheArchivos = recibido.Archivos : cacheAvisos = recibido.Avisos
            End If
            lblIndiceInfo.Text = If(recibido.ErrorLectura <> "", "No se pudieron cargar los indices.", recibido.Archivos.ToString() & " indices cargados" & If(recibido.Avisos > 0, " (parcial)", ""))
            If recibido.Codigo <> "" Then
                If recibido.ErrorLectura <> "" Then
                    lblEstado.Text = recibido.ErrorLectura
                Else
                    _resultadosBusqueda = recibido.Coincidencias
                    _codigoBusquedaActual = recibido.Codigo
                    _resultadoTruncadoActual = recibido.Truncado
                    AplicarFiltroResultados()
                End If
            End If
        End If
        If Not datosPendientes Then Return
        SyncLock bloqueoDatos
            If leyendoDatos OrElse cerradoDatos Then Return
            leyendoDatos = True
        End SyncLock
        datosPendientes = False
        Dim solicitud As New ResultadoCarga()
        solicitud.Carpeta = carpetaPendiente : solicitud.Codigo = codigoPendiente : solicitud.Version = versionDatos
        If String.Equals(cacheCarpeta, solicitud.Carpeta, System.StringComparison.OrdinalIgnoreCase) AndAlso _indice IsNot Nothing Then
            ' Copia superficial: el hilo de interfaz puede quitar entradas de
            ' _indice mientras el hilo de busqueda la esta recorriendo.
            solicitud.Indice = New System.Collections.Generic.List(Of String())(_indice)
            solicitud.Archivos = cacheArchivos : solicitud.Avisos = cacheAvisos
        End If
        Dim hilo As New System.Threading.Thread(Sub() LeerYBuscarDatos(solicitud))
        hilo.IsBackground = True
        hilo.Start()
    End Sub

    Private Sub LeerYBuscarDatos(solicitud As ResultadoCarga)
        Try
            If solicitud.Indice Is Nothing Then
                Dim lista As New System.Collections.Generic.List(Of String())
                Dim vistos As New System.Collections.Generic.HashSet(Of String)(System.StringComparer.OrdinalIgnoreCase)
                For Each archivo As String In System.IO.Directory.GetFiles(solicitud.Carpeta, "IndiceBuscador_*.txt")
                    Try
                        Using lector As New System.IO.StreamReader(archivo, System.Text.Encoding.UTF8)
                            While Not lector.EndOfStream
                                If cerradoDatos Then Return
                                Dim linea As String = lector.ReadLine()
                                If String.IsNullOrWhiteSpace(linea) OrElse linea.StartsWith("#") Then Continue While
                                Dim p As String() = linea.Split(ChrW(9))
                                Dim ticks As Long
                                If p.Length < 2 OrElse Not Long.TryParse(p(1), ticks) Then Continue While
                                Dim ruta As String = p(0).Trim()
                                If ruta = "" OrElse Not vistos.Add(ruta) Then Continue While
                                lista.Add(New String() {ruta, System.IO.Path.GetFileNameWithoutExtension(ruta).ToLowerInvariant(), System.IO.Path.GetExtension(ruta).ToLowerInvariant(), ticks.ToString(), If(p.Length > 2, p(2).ToLowerInvariant(), ""), If(p.Length > 3, p(3).ToLowerInvariant(), "")})
                            End While
                        End Using
                        solicitud.Archivos += 1
                    Catch
                        solicitud.Avisos += 1
                    End Try
                Next
                If solicitud.Archivos = 0 Then Throw New System.Exception("No se pudo leer ningun indice de archivos.")
                solicitud.Indice = lista
            End If
            solicitud.Coincidencias = New System.Collections.Generic.List(Of String())
            If solicitud.Codigo <> "" Then
                Dim codigo As String = solicitud.Codigo.ToLowerInvariant()
                For Each entrada As String() In solicitud.Indice
                    If cerradoDatos Then Return
                    If EsCopiaSeguridad(entrada(0)) Then Continue For
                    If entrada(1).Contains(codigo) OrElse entrada(4).Contains(codigo) OrElse entrada(5).Contains(codigo) Then
                        solicitud.Coincidencias.Add(entrada)
                        If solicitud.Coincidencias.Count >= MAX_RESULTADOS Then solicitud.Truncado = True : Exit For
                    End If
                Next
                solicitud.Coincidencias.Sort(Function(a As String(), b As String()) CLng(b(3)).CompareTo(CLng(a(3))))
            End If
        Catch ex As System.Exception
            solicitud.ErrorLectura = "No se pudieron leer los indices: " & ex.Message
        Finally
            SyncLock bloqueoDatos
                If Not cerradoDatos Then resultadoDatos = solicitud
                leyendoDatos = False
            End SyncLock
        End Try
    End Sub

    Private Sub ActualizarInfoIndice()
        If lblIndiceInfo Is Nothing Then Return
        PedirDatos("", True)
    End Sub

    Private Sub OnBuscar(sender As Object, e As System.EventArgs)
        DetenerRelojBusqueda()
        _focoTrasResultados = True
        Dim codigo As String = txtCodigo.Text.Trim()
        If codigo = "" Then
            lblEstado.Text = "Escribe un codigo para buscar."
            Return
        End If
        If panelUsos IsNot Nothing Then panelUsos.CambiarCarpeta(CarpetaIndice())
        PedirDatos(codigo)
    End Sub

    Private Sub OnFiltroTipoChanged(sender As Object, e As System.EventArgs)
        Dim rdo As System.Windows.Forms.RadioButton = TryCast(sender, System.Windows.Forms.RadioButton)
        If rdo Is Nothing OrElse Not rdo.Checked Then Return
        If _resultadosBusqueda Is Nothing Then Return

        ' Solo vuelve a dibujar la lista. No lee el indice y no repite la busqueda.
        AplicarFiltroResultados()
    End Sub

    Private Sub AplicarFiltroResultados()
        If _resultadosBusqueda Is Nothing Then Return

        Dim exts As System.Collections.Generic.List(Of String) = ExtensionesActivas()
        Dim visibles As Integer = 0

        lstResultados.BeginUpdate()
        Try
            lstResultados.Items.Clear()

            For Each entrada As String() In _resultadosBusqueda
                If entrada Is Nothing OrElse entrada.Length < 6 Then Continue For
                If Not exts.Contains(entrada(2)) Then Continue For

                lstResultados.Items.Add(CrearItemResultado(entrada))
                visibles += 1
            Next

            AplicarEstiloFilas()
        Finally
            lstResultados.EndUpdate()
        End Try

        Dim tipo As String = "todos los tipos"
        If rdoPiezas.Checked Then
            tipo = "piezas"
        ElseIf rdoEnsamblajes.Checked Then
            tipo = "ensamblajes"
        ElseIf rdoPlanos.Checked Then
            tipo = "planos"
        End If

        lblResultados.Text = visibles.ToString() & " resultado(s) encontrados" & _
            If(_resultadoTruncadoActual, " (limite " & MAX_RESULTADOS.ToString() & ")", "")

        lblEstado.Text = visibles.ToString() & " resultado(s) de " & tipo & _
            " para """ & _codigoBusquedaActual & """."

        If lstResultados.Items.Count > 0 Then
            lstResultados.Items(0).Selected = True
            If _focoTrasResultados Then lstResultados.Select()
        Else
            ActualizarSeleccion()
        End If
        _focoTrasResultados = False
    End Sub

    Private Function CrearItemResultado(entrada As String()) As System.Windows.Forms.ListViewItem
        Dim ruta As String = entrada(0)
        Dim item As New System.Windows.Forms.ListViewItem(System.IO.Path.GetFileName(ruta))
        item.SubItems.Add(entrada(2).ToUpper().Replace(".", ""))

        Dim fechaStr As String = ""
        Try
            fechaStr = New System.DateTime(CLng(entrada(3))).ToString("yyyy-MM-dd HH:mm")
        Catch
        End Try

        item.SubItems.Add(fechaStr)
        item.SubItems.Add(System.IO.Path.GetDirectoryName(ruta))
        item.Tag = ruta
        Return item
    End Function

    ' Filas alternas adaptadas al tema actual. Se usa reflexion para no crear
    ' una referencia directa de compilacion a System.Drawing.
    Private Sub AplicarEstiloFilas()
        Dim colorType As System.Type = TipoColorSistema()
        If colorType Is Nothing Then
            lstResultados.GridLines = True
            Return
        End If

        Try
            Dim tipos() As System.Type = New System.Type() { _
                GetType(Integer), GetType(Integer), GetType(Integer)}
            Dim metodo As System.Reflection.MethodInfo = colorType.GetMethod("FromArgb", tipos)
            Dim propiedadFondo As System.Reflection.PropertyInfo = _
                GetType(System.Windows.Forms.ListViewItem).GetProperty("BackColor")
            Dim propiedadTexto As System.Reflection.PropertyInfo = _
                GetType(System.Windows.Forms.ListViewItem).GetProperty("ForeColor")

            If metodo Is Nothing OrElse propiedadFondo Is Nothing Then
                lstResultados.GridLines = True
                Return
            End If

            Dim filaA As Object
            Dim filaB As Object
            Dim texto As Object

            If TemaOscuroActivo() Then
                filaA = metodo.Invoke(Nothing, New Object() {38, 48, 61})
                filaB = metodo.Invoke(Nothing, New Object() {44, 55, 69})
                texto = metodo.Invoke(Nothing, New Object() {214, 220, 228})
            Else
                filaA = metodo.Invoke(Nothing, New Object() {255, 255, 255})
                filaB = metodo.Invoke(Nothing, New Object() {236, 240, 245})
                texto = metodo.Invoke(Nothing, New Object() {28, 28, 30})
            End If

            For i As Integer = 0 To lstResultados.Items.Count - 1
                Dim colorFila As Object = If((i Mod 2) = 0, filaA, filaB)
                propiedadFondo.SetValue(lstResultados.Items(i), colorFila, Nothing)
                If propiedadTexto IsNot Nothing Then
                    propiedadTexto.SetValue(lstResultados.Items(i), texto, Nothing)
                End If
            Next
            lstResultados.GridLines = False
        Catch
            lstResultados.GridLines = True
        End Try
    End Sub

    Private Sub OnColumnClick(sender As Object, e As System.Windows.Forms.ColumnClickEventArgs)
        OrdenarPorColumna(e.Column)
    End Sub

    Private Sub OrdenarPorColumna(columna As Integer)
        If columna = _ordenActual Then
            _ascendente = Not _ascendente
        Else
            _ordenActual = columna
            _ascendente = True
        End If

        Dim sorter As New ColumnSorter(_ordenActual, _ascendente)
        lstResultados.ListViewItemSorter = sorter
        lstResultados.Sort()
        AplicarEstiloFilas()
    End Sub

    Private Sub OnCancelar(sender As Object, e As System.EventArgs)
        cancelar = True
        If ProcesoRelacionesActivo() Then SolicitarCancelacionRelaciones()
        lblEstado.Text = "Cancelando..."
        btnCancelar.Enabled = False
    End Sub

    ' ================= ACCIONES SOBRE RESULTADOS =================
    Private Function RutasSeleccionadas(Optional exigirExistencia As Boolean = True) _
            As System.Collections.Generic.List(Of String)
        Dim rutas As New System.Collections.Generic.List(Of String)

        If lstResultados.SelectedItems.Count = 0 Then
            System.Windows.Forms.MessageBox.Show("Selecciona uno o varios ficheros de la lista.", _
                "Buscador", System.Windows.Forms.MessageBoxButtons.OK, _
                System.Windows.Forms.MessageBoxIcon.Information)
            Return rutas
        End If

        Dim seleccion As New System.Collections.Generic.List(Of System.Windows.Forms.ListViewItem)
        For Each item As System.Windows.Forms.ListViewItem In lstResultados.SelectedItems
            seleccion.Add(item)
        Next

        Dim inexistentes As New System.Collections.Generic.List(Of String)
        For Each item As System.Windows.Forms.ListViewItem In seleccion
            If item.Tag Is Nothing Then Continue For
            Dim ruta As String = item.Tag.ToString()
            If ruta = "" Then Continue For

            If exigirExistencia AndAlso Not System.IO.File.Exists(ruta) Then
                inexistentes.Add(ruta)
                Continue For
            End If

            rutas.Add(ruta)
        Next

        If inexistentes.Count > 0 Then
            For Each ruta As String In inexistentes
                QuitarRutaDeInterfazYMemoria(ruta)
            Next
            EliminarRutasDeIndices(inexistentes.ToArray())

            System.Windows.Forms.MessageBox.Show( _
                inexistentes.Count.ToString() & " fichero(s) ya no existen." & vbCrLf & _
                "Se han quitado de los resultados y del indice.", _
                "Ficheros no encontrados", System.Windows.Forms.MessageBoxButtons.OK, _
                System.Windows.Forms.MessageBoxIcon.Warning)
        End If

        Return rutas
    End Function

    Private Function RutaSeleccionada() As String
        Dim rutas As System.Collections.Generic.List(Of String) = RutasSeleccionadas(True)
        If rutas.Count = 0 Then Return ""
        Return rutas(0)
    End Function

    Private Sub OnResultadosKeyDown(sender As Object, e As System.Windows.Forms.KeyEventArgs)
        If e.KeyCode = System.Windows.Forms.Keys.Delete Then
            OnBorrarFicheros(sender, e)
            e.Handled = True
            e.SuppressKeyPress = True
        ElseIf e.Control AndAlso e.KeyCode = System.Windows.Forms.Keys.C Then
            OnCopiarRuta(sender, e)
            e.Handled = True
            e.SuppressKeyPress = True
        ElseIf e.KeyCode = System.Windows.Forms.Keys.Enter Then
            OnAbrir(sender, e)
            e.Handled = True
            e.SuppressKeyPress = True
        ElseIf e.KeyCode = System.Windows.Forms.Keys.Escape Then
            e.Handled = True
            e.SuppressKeyPress = True
            CerrarBuscador()
        End If
    End Sub

    Private Sub ActualizarSeleccion()
        If lblSeleccion Is Nothing OrElse lstResultados Is Nothing Then Return
        Dim n As Integer = lstResultados.SelectedItems.Count
        If n = 0 Then
            lblSeleccion.Text = "Ningun fichero seleccionado"
        ElseIf n = 1 Then
            lblSeleccion.Text = "1 fichero seleccionado"
        Else
            lblSeleccion.Text = n.ToString() & " ficheros seleccionados"
        End If
    End Sub

    Private Sub OnSeleccionResultadosChanged(sender As Object, e As System.EventArgs)
        ActualizarPanelUsos()
        ActualizarSeleccion()
        ActualizarEstadoMenuContextual()
    End Sub

    Private Function BuscarDocumentoAbierto(ruta As String) As Inventor.Document
        Try
            For Each doc As Inventor.Document In oApp.Documents
                Try
                    If String.Equals(doc.FullFileName, ruta, _
                            System.StringComparison.OrdinalIgnoreCase) Then
                        Return doc
                    End If
                Catch
                End Try
            Next
        Catch
        End Try
        Return Nothing
    End Function

    Private Sub OnAbrir(sender As Object, e As System.EventArgs)
        If AperturaInventorSegura.EnCurso Then Return
        If BloquearAccionSiIndexa() Then Return
        Dim rutas As System.Collections.Generic.List(Of String) = RutasSeleccionadas(True)
        If rutas.Count = 0 Then Return

        Dim abiertos As Integer = 0
        Dim errores As New System.Collections.Generic.List(Of String)
        Dim visibleAnterior As Boolean = Me.Visible
        Me.Cursor = System.Windows.Forms.Cursors.WaitCursor
        Try
            ' Deja que Inventor muestre sus avisos delante del buscador.
            If visibleAnterior Then Me.Hide()
            For Each ruta As String In rutas
                Try
                    AperturaInventorSegura.Abrir(oApp, ruta)
                    abiertos += 1
                Catch ex As System.Exception
                    errores.Add(ex.Message)
                End Try
            Next
        Finally
            If Not Me.IsDisposed Then
                Me.Cursor = System.Windows.Forms.Cursors.Default
                If visibleAnterior Then Me.Show()
            End If
        End Try

        If Me.IsDisposed Then Return
        lblEstado.Text = abiertos.ToString() & " fichero(s) abierto(s) en Inventor."
        If errores.Count > 0 Then
            System.Windows.Forms.MessageBox.Show(Me, "No se pudieron abrir algunos ficheros:" & _
                vbCrLf & vbCrLf & String.Join(vbCrLf & vbCrLf, errores.ToArray()), _
                "Error al abrir", System.Windows.Forms.MessageBoxButtons.OK, _
                System.Windows.Forms.MessageBoxIcon.Error)
        End If
    End Sub

    Private Sub OnAbrirCarpeta(sender As Object, e As System.EventArgs)
        If BloquearAccionSiIndexa() Then Return
        Dim ruta As String = RutaSeleccionada()
        If ruta = "" Then Return
        Try
            System.Diagnostics.Process.Start("explorer.exe", "/select,""" & ruta & """")
        Catch ex As System.Exception
            System.Windows.Forms.MessageBox.Show("No se pudo abrir el Explorador:" & vbCrLf & _
                ex.Message, "Abrir carpeta", System.Windows.Forms.MessageBoxButtons.OK, _
                System.Windows.Forms.MessageBoxIcon.Error)
        End Try
    End Sub

    Private Sub OnCopiarRuta(sender As Object, e As System.EventArgs)
        If BloquearAccionSiIndexa() Then Return
        Dim rutas As System.Collections.Generic.List(Of String) = RutasSeleccionadas(False)
        If rutas.Count = 0 Then Return

        Try
            System.Windows.Forms.Clipboard.SetText(String.Join(vbCrLf, rutas.ToArray()))
            lblEstado.Text = rutas.Count.ToString() & " ruta(s) copiada(s) al portapapeles."
        Catch ex As System.Exception
            System.Windows.Forms.MessageBox.Show("No se pudieron copiar las rutas:" & vbCrLf & _
                ex.Message, "Copiar rutas", System.Windows.Forms.MessageBoxButtons.OK, _
                System.Windows.Forms.MessageBoxIcon.Error)
        End Try
    End Sub

    Private Sub OnCopiarFicheros(sender As Object, e As System.EventArgs)
        If BloquearAccionSiIndexa() Then Return
        Dim rutas As System.Collections.Generic.List(Of String) = RutasSeleccionadas(True)
        If rutas.Count = 0 Then Return

        Dim destino As String = ElegirCarpeta("")
        If destino = "" Then Return

        Dim copiados As Integer = 0
        Dim omitidos As Integer = 0
        Dim errores As New System.Collections.Generic.List(Of String)
        Me.Cursor = System.Windows.Forms.Cursors.WaitCursor

        For Each origen As String In rutas
            Dim destinoFinal As String = System.IO.Path.Combine(destino, System.IO.Path.GetFileName(origen))
            Try
                If String.Equals(origen, destinoFinal, System.StringComparison.OrdinalIgnoreCase) Then
                    omitidos += 1
                    Continue For
                End If

                Dim sobrescribir As Boolean = False
                If System.IO.File.Exists(destinoFinal) Then
                    Me.Cursor = System.Windows.Forms.Cursors.Default
                    Dim resp As System.Windows.Forms.DialogResult = System.Windows.Forms.MessageBox.Show( _
                        "Ya existe el fichero:" & vbCrLf & destinoFinal & vbCrLf & vbCrLf & _
                        "¿Quieres sobrescribirlo?", "Copiar fichero", _
                        System.Windows.Forms.MessageBoxButtons.YesNoCancel, _
                        System.Windows.Forms.MessageBoxIcon.Question)
                    Me.Cursor = System.Windows.Forms.Cursors.WaitCursor

                    If resp = System.Windows.Forms.DialogResult.Cancel Then Exit For
                    If resp = System.Windows.Forms.DialogResult.No Then
                        omitidos += 1
                        Continue For
                    End If
                    sobrescribir = True
                End If

                System.IO.File.Copy(origen, destinoFinal, sobrescribir)
                copiados += 1
            Catch ex As System.Exception
                errores.Add(System.IO.Path.GetFileName(origen) & ": " & ex.Message)
            End Try
        Next

        Me.Cursor = System.Windows.Forms.Cursors.Default
        lblEstado.Text = copiados.ToString() & " copiado(s), " & _
            omitidos.ToString() & " omitido(s)."

        If errores.Count > 0 Then
            System.Windows.Forms.MessageBox.Show("Se produjeron errores al copiar:" & _
                vbCrLf & vbCrLf & String.Join(vbCrLf, errores.ToArray()), _
                "Copiar ficheros", System.Windows.Forms.MessageBoxButtons.OK, _
                System.Windows.Forms.MessageBoxIcon.Warning)
        ElseIf copiados > 0 Then
            Dim respAbrir As System.Windows.Forms.DialogResult = System.Windows.Forms.MessageBox.Show( _
                "Copia terminada correctamente." & vbCrLf & _
                "Si la carpeta esta indexada, pulsa Actualizar para incorporar la copia." & _
                vbCrLf & vbCrLf & "¿Abrir la carpeta de destino?", "Copiar ficheros", _
                System.Windows.Forms.MessageBoxButtons.YesNo, _
                System.Windows.Forms.MessageBoxIcon.Information)
            If respAbrir = System.Windows.Forms.DialogResult.Yes Then
                Try
                    System.Diagnostics.Process.Start("explorer.exe", """" & destino & """")
                Catch
                End Try
            End If
        End If
    End Sub

    Private Sub MoverArchivoSeguro(origen As String, destino As String)
        ' File.Move puede fallar entre unidades distintas. En ese caso se hace
        ' copia + borrado, eliminando la copia si no se puede retirar el origen.
        Try
            System.IO.File.Move(origen, destino)
            Return
        Catch exMove As System.IO.IOException
            System.IO.File.Copy(origen, destino, False)
            Try
                System.IO.File.Delete(origen)
            Catch exDelete As System.Exception
                Try
                    If System.IO.File.Exists(destino) Then System.IO.File.Delete(destino)
                Catch
                End Try
                Throw New System.Exception( _
                    "se copio al destino pero no se pudo borrar el origen: " & exDelete.Message)
            End Try
        End Try
    End Sub

    Private Sub OnMoverFicheros(sender As Object, e As System.EventArgs)
        If BloquearAccionSiIndexa() Then Return
        Dim rutas As System.Collections.Generic.List(Of String) = RutasSeleccionadas(True)
        If rutas.Count = 0 Then Return

        Dim destino As String = ElegirCarpeta("")
        If destino = "" Then Return

        Dim aviso As String = _
            "Mover archivos IPT, IAM o IDW puede romper referencias entre piezas, " & _
            "ensamblajes y planos si Inventor no puede resolver la nueva ubicacion." & _
            vbCrLf & vbCrLf & _
            "Se moveran " & rutas.Count.ToString() & " fichero(s) a:" & vbCrLf & _
            destino & vbCrLf & vbCrLf & "¿Quieres continuar?"

        Dim confirmar As System.Windows.Forms.DialogResult = System.Windows.Forms.MessageBox.Show( _
            aviso, "CONFIRMAR MOVIMIENTO", System.Windows.Forms.MessageBoxButtons.YesNo, _
            System.Windows.Forms.MessageBoxIcon.Warning, _
            System.Windows.Forms.MessageBoxDefaultButton.Button2)
        If confirmar <> System.Windows.Forms.DialogResult.Yes Then Return

        Dim movimientos As New System.Collections.Generic.Dictionary(Of String, String)( _
            System.StringComparer.OrdinalIgnoreCase)
        Dim omitidos As Integer = 0
        Dim errores As New System.Collections.Generic.List(Of String)
        Me.Cursor = System.Windows.Forms.Cursors.WaitCursor

        For Each origen As String In rutas
            Dim destinoFinal As String = System.IO.Path.Combine(destino, _
                System.IO.Path.GetFileName(origen))
            Dim respaldoDestino As String = ""

            Try
                If String.Equals(origen, destinoFinal, _
                        System.StringComparison.OrdinalIgnoreCase) Then
                    omitidos += 1
                    Continue For
                End If

                Dim docOrigen As Inventor.Document = BuscarDocumentoAbierto(origen)
                If docOrigen IsNot Nothing Then
                    If docOrigen.Dirty Then
                        Throw New System.Exception( _
                            "esta abierto en Inventor y tiene cambios sin guardar")
                    End If
                    docOrigen.Close(True)
                End If

                If System.IO.File.Exists(destinoFinal) Then
                    Me.Cursor = System.Windows.Forms.Cursors.Default
                    Dim resp As System.Windows.Forms.DialogResult = System.Windows.Forms.MessageBox.Show( _
                        "Ya existe el fichero de destino:" & vbCrLf & destinoFinal & _
                        vbCrLf & vbCrLf & "¿Quieres sustituirlo?", "Mover fichero", _
                        System.Windows.Forms.MessageBoxButtons.YesNoCancel, _
                        System.Windows.Forms.MessageBoxIcon.Question, _
                        System.Windows.Forms.MessageBoxDefaultButton.Button2)
                    Me.Cursor = System.Windows.Forms.Cursors.WaitCursor

                    If resp = System.Windows.Forms.DialogResult.Cancel Then Exit For
                    If resp = System.Windows.Forms.DialogResult.No Then
                        omitidos += 1
                        Continue For
                    End If

                    Dim docDestino As Inventor.Document = BuscarDocumentoAbierto(destinoFinal)
                    If docDestino IsNot Nothing Then
                        If docDestino.Dirty Then
                            Throw New System.Exception( _
                                "el fichero de destino esta abierto y tiene cambios sin guardar")
                        End If
                        docDestino.Close(True)
                    End If

                    Dim atributosDestino As System.IO.FileAttributes = _
                        System.IO.File.GetAttributes(destinoFinal)
                    If (atributosDestino And System.IO.FileAttributes.ReadOnly) = _
                            System.IO.FileAttributes.ReadOnly Then
                        System.IO.File.SetAttributes(destinoFinal, _
                            atributosDestino And Not System.IO.FileAttributes.ReadOnly)
                    End If

                    respaldoDestino = destinoFinal & ".mover_backup_" & _
                        System.Guid.NewGuid().ToString("N")
                    System.IO.File.Move(destinoFinal, respaldoDestino)
                End If

                Dim atributosOrigen As System.IO.FileAttributes = _
                    System.IO.File.GetAttributes(origen)
                If (atributosOrigen And System.IO.FileAttributes.ReadOnly) = _
                        System.IO.FileAttributes.ReadOnly Then
                    System.IO.File.SetAttributes(origen, _
                        atributosOrigen And Not System.IO.FileAttributes.ReadOnly)
                End If

                MoverArchivoSeguro(origen, destinoFinal)
                If System.IO.File.Exists(origen) OrElse _
                        Not System.IO.File.Exists(destinoFinal) Then
                    Throw New System.Exception("Windows no confirmo el movimiento completo")
                End If

                movimientos(origen) = destinoFinal

                If respaldoDestino <> "" AndAlso System.IO.File.Exists(respaldoDestino) Then
                    Try
                        System.IO.File.Delete(respaldoDestino)
                    Catch
                    End Try
                End If
            Catch ex As System.Exception
                ' Si se habia apartado un destino anterior, se restaura para no perderlo.
                Try
                    If respaldoDestino <> "" AndAlso System.IO.File.Exists(respaldoDestino) Then
                        If System.IO.File.Exists(destinoFinal) Then System.IO.File.Delete(destinoFinal)
                        System.IO.File.Move(respaldoDestino, destinoFinal)
                    End If
                Catch exRestore As System.Exception
                    errores.Add(System.IO.Path.GetFileName(origen) & _
                        ": fallo al restaurar el destino anterior: " & exRestore.Message)
                End Try
                errores.Add(System.IO.Path.GetFileName(origen) & ": " & ex.Message)
            End Try
        Next

        Dim erroresIndice As System.Collections.Generic.List(Of String) = _
            ActualizarMovimientosEnIndices(movimientos)
        ActualizarMovimientosEnMemoria(movimientos)
        AplicarFiltroResultados()

        Me.Cursor = System.Windows.Forms.Cursors.Default
        lblEstado.Text = movimientos.Count.ToString() & " movido(s), " & _
            omitidos.ToString() & " omitido(s)."

        If errores.Count > 0 OrElse erroresIndice.Count > 0 Then
            Dim msg As New System.Text.StringBuilder()
            If errores.Count > 0 Then
                msg.AppendLine("Ficheros que no se pudieron mover:")
                msg.AppendLine(String.Join(vbCrLf, errores.ToArray()))
            End If
            If erroresIndice.Count > 0 Then
                If msg.Length > 0 Then msg.AppendLine()
                msg.AppendLine("Avisos al actualizar los indices:")
                msg.AppendLine(String.Join(vbCrLf, erroresIndice.ToArray()))
            End If
            System.Windows.Forms.MessageBox.Show(msg.ToString(), "Resultado del movimiento", _
                System.Windows.Forms.MessageBoxButtons.OK, _
                System.Windows.Forms.MessageBoxIcon.Warning)
        ElseIf movimientos.Count > 0 Then
            Dim abrir As System.Windows.Forms.DialogResult = System.Windows.Forms.MessageBox.Show( _
                "Movimiento terminado y rutas del indice actualizadas." & vbCrLf & _
                "¿Abrir la carpeta de destino?", "Mover ficheros", _
                System.Windows.Forms.MessageBoxButtons.YesNo, _
                System.Windows.Forms.MessageBoxIcon.Information)
            If abrir = System.Windows.Forms.DialogResult.Yes Then
                Try
                    System.Diagnostics.Process.Start("explorer.exe", """" & destino & """")
                Catch
                End Try
            End If
        End If
    End Sub

    Private Function RutaDentroDeRaiz(ruta As String, raiz As String) As Boolean
        Try
            Dim rutaCompleta As String = System.IO.Path.GetFullPath(ruta).TrimEnd("\"c)
            Dim raizCompleta As String = System.IO.Path.GetFullPath(raiz).TrimEnd("\"c)

            If String.Equals(rutaCompleta, raizCompleta, _
                    System.StringComparison.OrdinalIgnoreCase) Then Return True

            Return rutaCompleta.StartsWith(raizCompleta & "\", _
                System.StringComparison.OrdinalIgnoreCase)
        Catch
            Return ruta.StartsWith(raiz, System.StringComparison.OrdinalIgnoreCase)
        End Try
    End Function

    Private Function RutaEstaEnAlgunaRaizIndexada(ruta As String) As Boolean
        For Each archivo As String In ListarArchivosIndice()
            Dim raiz As String = RaizDeIndice(archivo)
            If raiz <> "" AndAlso RutaDentroDeRaiz(ruta, raiz) Then Return True
        Next
        Return False
    End Function

    Private Function MetadatosDeRuta(ruta As String) As String()
        If _indice IsNot Nothing Then
            For Each entrada As String() In _indice
                If entrada IsNot Nothing AndAlso entrada.Length >= 6 AndAlso _
                        String.Equals(entrada(0), ruta, _
                        System.StringComparison.OrdinalIgnoreCase) Then
                    Return New String() {entrada(4), entrada(5)}
                End If
            Next
        End If
        Return New String() {"", ""}
    End Function

    Private Function ActualizarMovimientosEnIndices( _
            movimientos As System.Collections.Generic.Dictionary(Of String, String)) _
            As System.Collections.Generic.List(Of String)

        Dim errores As New System.Collections.Generic.List(Of String)
        If movimientos Is Nothing OrElse movimientos.Count = 0 Then Return errores

        Dim metadatos As New System.Collections.Generic.Dictionary(Of String, String())( _
            System.StringComparer.OrdinalIgnoreCase)
        For Each par As System.Collections.Generic.KeyValuePair(Of String, String) In movimientos
            metadatos(par.Key) = MetadatosDeRuta(par.Key)
        Next

        For Each archivo As String In ListarArchivosIndice()
            Dim temporal As String = archivo & ".mover.tmp"
            Try
                Dim lineas() As String = LeerLineasIndiceConReintento(archivo, 5, 200)
                Dim raiz As String = RaizDeIndice(archivo)
                Dim salida As New System.Collections.Generic.List(Of String)
                Dim rutasSalida As New System.Collections.Generic.HashSet(Of String)( _
                    System.StringComparer.OrdinalIgnoreCase)
                Dim modificado As Boolean = False

                For Each linea As String In lineas
                    If linea Is Nothing Then Continue For
                    If linea.StartsWith("#") OrElse linea.Trim() = "" Then
                        salida.Add(linea)
                        Continue For
                    End If

                    Dim p() As String = linea.Split(CChar(vbTab))
                    If p.Length = 0 Then Continue For
                    Dim rutaLinea As String = p(0).Trim()

                    If movimientos.ContainsKey(rutaLinea) Then
                        If p.Length >= 3 AndAlso p(2).Trim() <> "" Then
                            metadatos(rutaLinea)(0) = p(2).Trim()
                        End If
                        If p.Length >= 4 AndAlso p(3).Trim() <> "" Then
                            metadatos(rutaLinea)(1) = p(3).Trim()
                        End If
                        modificado = True
                        Continue For
                    End If

                    Dim esDestino As Boolean = False
                    For Each destino As String In movimientos.Values
                        If String.Equals(rutaLinea, destino, _
                                System.StringComparison.OrdinalIgnoreCase) Then
                            esDestino = True
                            Exit For
                        End If
                    Next
                    If esDestino Then
                        modificado = True
                        Continue For
                    End If

                    salida.Add(linea)
                    rutasSalida.Add(rutaLinea)
                Next

                For Each par As System.Collections.Generic.KeyValuePair(Of String, String) In movimientos
                    Dim destino As String = par.Value
                    If raiz <> "" AndAlso RutaDentroDeRaiz(destino, raiz) AndAlso _
                            System.IO.File.Exists(destino) AndAlso Not rutasSalida.Contains(destino) Then

                        Dim ticks As Long = System.IO.File.GetLastWriteTime(destino).Ticks
                        Dim md() As String = metadatos(par.Key)
                        salida.Add(destino & vbTab & ticks.ToString() & vbTab & _
                            md(0).Replace(vbTab, " ") & vbTab & md(1).Replace(vbTab, " "))
                        rutasSalida.Add(destino)
                        modificado = True
                    End If
                Next

                If modificado Then
                    Using sw As New System.IO.StreamWriter(temporal, False, _
                            New System.Text.UTF8Encoding(False))
                        For Each linea As String In salida
                            sw.WriteLine(linea)
                        Next
                    End Using
                    ReemplazarIndiceDeFormaSegura(temporal, archivo)
                End If
            Catch ex As System.Exception
                errores.Add(System.IO.Path.GetFileName(archivo) & ": " & ex.Message)
                Try
                    If System.IO.File.Exists(temporal) Then System.IO.File.Delete(temporal)
                Catch
                End Try
            End Try
        Next

        _indiceFirma = FirmaIndices(ListarArchivosIndice())
        ActualizarInfoIndice()
        Return errores
    End Function

    Private Sub ActualizarMovimientosEnMemoria( _
            movimientos As System.Collections.Generic.Dictionary(Of String, String))
        If movimientos Is Nothing OrElse movimientos.Count = 0 Then Return

        ActualizarListaPorMovimientos(_indice, movimientos)
        ActualizarListaPorMovimientos(_resultadosBusqueda, movimientos)
    End Sub

    Private Sub ActualizarListaPorMovimientos( _
            lista As System.Collections.Generic.List(Of String()), _
            movimientos As System.Collections.Generic.Dictionary(Of String, String))
        If lista Is Nothing Then Return

        For Each par As System.Collections.Generic.KeyValuePair(Of String, String) In movimientos
            Dim origen As String = par.Key
            Dim destino As String = par.Value

            lista.RemoveAll(Function(entrada As String()) _
                entrada IsNot Nothing AndAlso entrada.Length > 0 AndAlso _
                String.Equals(entrada(0), destino, _
                    System.StringComparison.OrdinalIgnoreCase))

            Dim encontrada As String() = Nothing
            For Each entrada As String() In lista
                If entrada IsNot Nothing AndAlso entrada.Length >= 6 AndAlso _
                        String.Equals(entrada(0), origen, _
                        System.StringComparison.OrdinalIgnoreCase) Then
                    encontrada = entrada
                    Exit For
                End If
            Next

            If encontrada IsNot Nothing Then
                If RutaEstaEnAlgunaRaizIndexada(destino) Then
                    encontrada(0) = destino
                    encontrada(1) = System.IO.Path.GetFileNameWithoutExtension(destino).ToLowerInvariant()
                    encontrada(2) = System.IO.Path.GetExtension(destino).ToLowerInvariant()
                    Try
                        encontrada(3) = System.IO.File.GetLastWriteTime(destino).Ticks.ToString()
                    Catch
                    End Try
                Else
                    lista.Remove(encontrada)
                End If
            End If
        Next
    End Sub

    ' Consulta independiente: lee referencias guardadas, nunca guarda documentos.
    Private Sub ActualizarPanelUsos()
        If panelUsos Is Nothing Then Return
        Dim seleccion As New System.Collections.Generic.List(Of String)
        For Each item As System.Windows.Forms.ListViewItem In lstResultados.SelectedItems
            If item.Tag Is Nothing Then Continue For
            Dim ruta As String = item.Tag.ToString()
            Dim ext As String = System.IO.Path.GetExtension(ruta).ToLowerInvariant()
            If ext = ".ipt" OrElse ext = ".iam" Then seleccion.Add(ruta)
        Next
        panelUsos.Consultar(seleccion, New System.Collections.Generic.List(Of String)(New String() {CarpetaIndice()}))
    End Sub

    Private Sub OnBorrarFicheros(sender As Object, e As System.EventArgs)
        If BloquearAccionSiIndexa() Then Return
        Dim rutas As System.Collections.Generic.List(Of String) = RutasSeleccionadas(True)
        If rutas.Count = 0 Then Return

        Dim resumen As New System.Text.StringBuilder()
        Dim maxMostrar As Integer = System.Math.Min(rutas.Count, 12)
        For i As Integer = 0 To maxMostrar - 1
            resumen.AppendLine("- " & rutas(i))
        Next
        If rutas.Count > maxMostrar Then
            resumen.AppendLine("... y " & (rutas.Count - maxMostrar).ToString() & " mas")
        End If

        Dim resp As System.Windows.Forms.DialogResult = System.Windows.Forms.MessageBox.Show( _
            "Se borraran definitivamente " & rutas.Count.ToString() & " fichero(s)." & _
            vbCrLf & "No se borraran automaticamente planos ni archivos relacionados." & _
            vbCrLf & vbCrLf & resumen.ToString() & vbCrLf & _
            "¿Confirmas el borrado?", "CONFIRMAR BORRADO", _
            System.Windows.Forms.MessageBoxButtons.YesNo, _
            System.Windows.Forms.MessageBoxIcon.Warning, _
            System.Windows.Forms.MessageBoxDefaultButton.Button2)

        If resp <> System.Windows.Forms.DialogResult.Yes Then Return

        Dim borradas As New System.Collections.Generic.List(Of String)
        Dim errores As New System.Collections.Generic.List(Of String)
        Me.Cursor = System.Windows.Forms.Cursors.WaitCursor

        For Each ruta As String In rutas
            Try
                Dim docAbierto As Inventor.Document = BuscarDocumentoAbierto(ruta)
                If docAbierto IsNot Nothing Then
                    If docAbierto.Dirty Then
                        Throw New System.Exception("esta abierto en Inventor y tiene cambios sin guardar")
                    End If
                    docAbierto.Close(True)
                End If

                Dim atributos As System.IO.FileAttributes = System.IO.File.GetAttributes(ruta)
                If (atributos And System.IO.FileAttributes.ReadOnly) = System.IO.FileAttributes.ReadOnly Then
                    System.IO.File.SetAttributes(ruta, atributos And Not System.IO.FileAttributes.ReadOnly)
                End If

                System.IO.File.Delete(ruta)
                If System.IO.File.Exists(ruta) Then
                    Throw New System.Exception("Windows no confirmo la eliminacion del fichero")
                End If

                borradas.Add(ruta)
                QuitarRutaDeInterfazYMemoria(ruta)
            Catch ex As System.Exception
                errores.Add(System.IO.Path.GetFileName(ruta) & ": " & ex.Message)
            End Try
        Next

        Dim erroresIndice As System.Collections.Generic.List(Of String) = _
            EliminarRutasDeIndices(borradas.ToArray())

        Me.Cursor = System.Windows.Forms.Cursors.Default
        lblEstado.Text = borradas.Count.ToString() & " fichero(s) borrado(s)."

        If errores.Count > 0 OrElse erroresIndice.Count > 0 Then
            Dim msg As New System.Text.StringBuilder()
            If errores.Count > 0 Then
                msg.AppendLine("Ficheros que no se pudieron borrar:")
                msg.AppendLine(String.Join(vbCrLf, errores.ToArray()))
            End If
            If erroresIndice.Count > 0 Then
                If msg.Length > 0 Then msg.AppendLine()
                msg.AppendLine("Avisos al actualizar los indices:")
                msg.AppendLine(String.Join(vbCrLf, erroresIndice.ToArray()))
            End If
            System.Windows.Forms.MessageBox.Show(msg.ToString(), "Resultado del borrado", _
                System.Windows.Forms.MessageBoxButtons.OK, _
                System.Windows.Forms.MessageBoxIcon.Warning)
        End If
    End Sub

    Private Sub QuitarRutaDeInterfazYMemoria(ruta As String)
        For i As Integer = lstResultados.Items.Count - 1 To 0 Step -1
            Dim item As System.Windows.Forms.ListViewItem = lstResultados.Items(i)
            If item.Tag IsNot Nothing AndAlso String.Equals(item.Tag.ToString(), ruta, _
                    System.StringComparison.OrdinalIgnoreCase) Then
                lstResultados.Items.RemoveAt(i)
            End If
        Next

        AplicarEstiloFilas()

        If _indice IsNot Nothing Then
            _indice.RemoveAll(Function(entrada As String()) _
                entrada IsNot Nothing AndAlso entrada.Length > 0 AndAlso _
                String.Equals(entrada(0), ruta, System.StringComparison.OrdinalIgnoreCase))
        End If

        If _resultadosBusqueda IsNot Nothing Then
            _resultadosBusqueda.RemoveAll(Function(entrada As String()) _
                entrada IsNot Nothing AndAlso entrada.Length > 0 AndAlso _
                String.Equals(entrada(0), ruta, System.StringComparison.OrdinalIgnoreCase))
        End If
    End Sub

    Private Function EliminarRutasDeIndices(rutas() As String) _
            As System.Collections.Generic.List(Of String)
        Dim errores As New System.Collections.Generic.List(Of String)
        If rutas Is Nothing OrElse rutas.Length = 0 Then Return errores

        Dim eliminar As New System.Collections.Generic.HashSet(Of String)( _
            System.StringComparer.OrdinalIgnoreCase)
        For Each ruta As String In rutas
            If Not String.IsNullOrWhiteSpace(ruta) Then eliminar.Add(ruta)
        Next

        For Each archivo As String In ListarArchivosIndice()
            Dim temporal As String = archivo & ".gestion.tmp"
            Try
                Dim lineas() As String = LeerLineasIndiceConReintento(archivo, 5, 200)
                Dim modificado As Boolean = False

                Using sw As New System.IO.StreamWriter(temporal, False, _
                        New System.Text.UTF8Encoding(False))
                    For Each linea As String In lineas
                        If linea Is Nothing Then Continue For

                        If linea.StartsWith("#") OrElse linea.Trim() = "" Then
                            sw.WriteLine(linea)
                            Continue For
                        End If

                        Dim p() As String = linea.Split(CChar(vbTab))
                        If p.Length > 0 AndAlso eliminar.Contains(p(0).Trim()) Then
                            modificado = True
                            Continue For
                        End If

                        sw.WriteLine(linea)
                    Next
                End Using

                If modificado Then
                    ReemplazarIndiceDeFormaSegura(temporal, archivo)
                ElseIf System.IO.File.Exists(temporal) Then
                    System.IO.File.Delete(temporal)
                End If
            Catch ex As System.Exception
                errores.Add(System.IO.Path.GetFileName(archivo) & ": " & ex.Message)
                Try
                    If System.IO.File.Exists(temporal) Then System.IO.File.Delete(temporal)
                Catch
                End Try
            End Try
        Next

        _indiceFirma = FirmaIndices(ListarArchivosIndice())
        ActualizarInfoIndice()
        Return errores
    End Function

End Class


' ================= ORDENADOR DE COLUMNAS =================
Public Class ColumnSorter
    Implements System.Collections.IComparer

    Private _columnIndex As Integer
    Private _ascendente As Boolean

    Public Sub New(columnIndex As Integer, ascendente As Boolean)
        _columnIndex = columnIndex
        _ascendente = ascendente
    End Sub

    Public Function Compare(x As Object, y As Object) As Integer Implements System.Collections.IComparer.Compare
        Dim itemX As System.Windows.Forms.ListViewItem = TryCast(x, System.Windows.Forms.ListViewItem)
        Dim itemY As System.Windows.Forms.ListViewItem = TryCast(y, System.Windows.Forms.ListViewItem)

        If itemX Is Nothing OrElse itemY Is Nothing Then Return 0

        Dim textoX As String = ""
        Dim textoY As String = ""

        If _columnIndex < itemX.SubItems.Count Then textoX = itemX.SubItems(_columnIndex).Text
        If _columnIndex < itemY.SubItems.Count Then textoY = itemY.SubItems(_columnIndex).Text

        Dim resultado As Integer

        ' Columnas: 0 Nombre, 1 Formato, 2 Modificado, 3 Ruta
        If _columnIndex = 2 Then
            Dim fechaX As DateTime = DateTime.MinValue
            Dim fechaY As DateTime = DateTime.MinValue
            DateTime.TryParse(textoX, fechaX)
            DateTime.TryParse(textoY, fechaY)
            resultado = fechaX.CompareTo(fechaY)
        Else
            resultado = String.Compare(textoX, textoY, True)
        End If

        If Not _ascendente Then resultado = -resultado
        Return resultado
    End Function

End Class


' Lee el mapa inverso componente -> ensamblajes que deja el proceso de
' relaciones y responde a la seleccion sin tocar el disco ni Inventor.
Public Class ConsultaUsosPanel
    Inherits System.Windows.Forms.UserControl

    Private Class DatosUsos
        Public Padres As New System.Collections.Generic.Dictionary(Of String, System.Collections.Generic.HashSet(Of String))(System.StringComparer.OrdinalIgnoreCase)
        Public Unidades As New System.Collections.Generic.Dictionary(Of String, String)(System.StringComparer.OrdinalIgnoreCase)
        Public Respuestas As New System.Collections.Generic.Dictionary(Of String, System.Collections.Generic.HashSet(Of String))(System.StringComparer.OrdinalIgnoreCase)
        Public IndicesLeidos As Integer
        Public Parcial As Boolean
        Public ErrorCarga As String = ""
    End Class

    Private listaEnsamblajes As System.Windows.Forms.ListView
    Private cabeceraUsos As System.Windows.Forms.Panel
    Private colFichero As System.Windows.Forms.Label
    Private estado As System.Windows.Forms.Label
    Private detalle As System.Windows.Forms.Label
    Private botonAbrir As System.Windows.Forms.Button
    Private oApp As Inventor.Application
    Private reloj As System.Windows.Forms.Timer
    Private seleccion As New System.Collections.Generic.List(Of String)
    Private carpeta As String = ""
    Private datos As DatosUsos
    Private terminado As DatosUsos
    Private carpetaTerminada As String = ""
    Private carga As Boolean = False
    Private pendiente As Boolean = False
    Private cerrado As Boolean = False
    Private ReadOnly bloqueo As New Object()

    Private Declare Unicode Function WNetGetConnection Lib "mpr.dll" Alias "WNetGetConnectionW" ( _
        localName As String, remoteName As System.Text.StringBuilder, ByRef length As Integer) As Integer

    Public Sub New(app As Inventor.Application)
        oApp = app

        listaEnsamblajes = New System.Windows.Forms.ListView()
        listaEnsamblajes.View = System.Windows.Forms.View.Details
        listaEnsamblajes.FullRowSelect = True : listaEnsamblajes.MultiSelect = True
        listaEnsamblajes.HideSelection = False : listaEnsamblajes.GridLines = False
        listaEnsamblajes.Dock = System.Windows.Forms.DockStyle.Fill
        listaEnsamblajes.Columns.Add("CODIGO", 130)
        listaEnsamblajes.Columns.Add("FICHERO", 250)
        AddHandler listaEnsamblajes.DoubleClick, AddressOf AbrirEnsamblajesSeleccionados
        AddHandler listaEnsamblajes.KeyDown, AddressOf OnTeclaEnsamblajes
        AddHandler listaEnsamblajes.SelectedIndexChanged, AddressOf OnEnsamblajeSeleccionado
        listaEnsamblajes.HeaderStyle = System.Windows.Forms.ColumnHeaderStyle.None
        AddHandler Me.Resize, AddressOf AjustarListaEnsamblajes

        estado = New System.Windows.Forms.Label()
        estado.Text = "ENSAMBLAJES VINCULADOS"
        estado.Height = 26
        estado.Dock = System.Windows.Forms.DockStyle.Top
        estado.Tag = "TENUE"

        botonAbrir = New System.Windows.Forms.Button()
        botonAbrir.Text = "Abrir ensamblaje IAM"
        botonAbrir.Height = 34
        botonAbrir.Dock = System.Windows.Forms.DockStyle.Bottom
        botonAbrir.Tag = "ACENTO"
        botonAbrir.TabStop = False
        botonAbrir.Enabled = False
        AddHandler botonAbrir.Click, AddressOf AbrirEnsamblajesSeleccionados

        detalle = New System.Windows.Forms.Label()
        detalle.Text = ""
        detalle.Height = 40
        detalle.Dock = System.Windows.Forms.DockStyle.Bottom
        detalle.Tag = "TENUE"

        ' Cabecera propia, porque la del sistema no admite color. Va antes que
        ' "estado" para que, con el acoplado inverso de WinForms, el rotulo
        ' quede arriba del todo y esta fila justo debajo.
        cabeceraUsos = New System.Windows.Forms.Panel()
        cabeceraUsos.Height = 24
        cabeceraUsos.Dock = System.Windows.Forms.DockStyle.Top
        cabeceraUsos.Tag = "CABTABLA"

        Dim colCodigo As New System.Windows.Forms.Label()
        colCodigo.Text = "CODIGO" : colCodigo.Left = 6 : colCodigo.Top = 6 : colCodigo.Width = 120
        colCodigo.Tag = "TEXTOACENTO"
        cabeceraUsos.Controls.Add(colCodigo)

        colFichero = New System.Windows.Forms.Label()
        colFichero.Text = "FICHERO" : colFichero.Left = 136 : colFichero.Top = 6 : colFichero.Width = 200
        colFichero.Tag = "TEXTOACENTO"
        colFichero.Anchor = System.Windows.Forms.AnchorStyles.Top _
            Or System.Windows.Forms.AnchorStyles.Left Or System.Windows.Forms.AnchorStyles.Right
        cabeceraUsos.Controls.Add(colFichero)

        ' El orden importa: primero el que rellena y despues los bordes.
        Me.Controls.Add(listaEnsamblajes)
        Me.Controls.Add(cabeceraUsos)
        Me.Controls.Add(estado)
        Me.Controls.Add(botonAbrir)
        Me.Controls.Add(detalle)

        MostrarMensaje("Selecciona una pieza.")

        reloj = New System.Windows.Forms.Timer()
        reloj.Interval = 100
        AddHandler reloj.Tick, AddressOf RecibirCarga
        AddHandler Me.Disposed, AddressOf AlCerrar
        reloj.Start()
    End Sub

    Public ReadOnly Property EnCurso As Boolean
        Get
            Return False ' La lectura del indice no debe impedir las acciones ni cerrar el buscador.
        End Get
    End Property

    Public Function PrepararCierre() As Boolean
        SyncLock bloqueo
            cerrado = True
        End SyncLock
        Try
            reloj.Stop()
        Catch
        End Try
        Return True
    End Function

    Private Sub AlCerrar(sender As Object, e As System.EventArgs)
        PrepararCierre()
        Try
            reloj.Dispose()
        Catch
        End Try
    End Sub

    Public Sub CambiarCarpeta(ruta As String, Optional forzar As Boolean = False)
        Dim nueva As String = ruta.Trim().TrimEnd("\"c)
        If nueva = "" Then Return
        If String.Equals(carpeta, nueva, System.StringComparison.OrdinalIgnoreCase) AndAlso Not forzar Then Return
        Dim distinta As Boolean = Not String.Equals(carpeta, nueva, System.StringComparison.OrdinalIgnoreCase)
        carpeta = nueva
        If distinta Then datos = Nothing
        pendiente = True
        IniciarCarga()
        MostrarSeleccion()
    End Sub

    Public Sub Consultar(piezas As System.Collections.Generic.List(Of String), carpetas As System.Collections.Generic.List(Of String))
        seleccion = New System.Collections.Generic.List(Of String)(piezas)
        If carpetas IsNot Nothing AndAlso carpetas.Count > 0 Then CambiarCarpeta(carpetas(0))
        MostrarSeleccion()
    End Sub

    Private Sub IniciarCarga()
        If Not pendiente Then Return
        SyncLock bloqueo
            If cerrado OrElse carga Then Return
            carga = True
        End SyncLock
        pendiente = False
        Dim destino As String = carpeta
        Dim hilo As New System.Threading.Thread(Sub() CargarRelaciones(destino))
        hilo.IsBackground = True
        hilo.Start()
    End Sub

    Private Function Cancelada() As Boolean
        SyncLock bloqueo
            Return cerrado
        End SyncLock
    End Function

    Private Sub RecibirCarga(sender As Object, e As System.EventArgs)
        Dim recibidos As DatosUsos = Nothing
        Dim origen As String = ""
        SyncLock bloqueo
            If terminado IsNot Nothing Then
                recibidos = terminado : origen = carpetaTerminada
                terminado = Nothing
            End If
        End SyncLock
        If recibidos IsNot Nothing AndAlso String.Equals(origen, carpeta, System.StringComparison.OrdinalIgnoreCase) Then
            ' Si falla la red, conserva los ultimos datos disponibles y marca el estado.
            If recibidos.IndicesLeidos = 0 AndAlso recibidos.ErrorCarga <> "" AndAlso datos IsNot Nothing Then
                datos.Parcial = True
            Else
                datos = recibidos
            End If
            MostrarSeleccion()
        End If
        IniciarCarga()
    End Sub

    Private Shared Function Clave(ruta As String, unidades As System.Collections.Generic.Dictionary(Of String, String)) As String
        Dim resultado As String = System.IO.Path.GetFullPath(ruta.Replace("/", "\"))
        If resultado.Length > 2 AndAlso resultado(1) = ":"c Then
            Dim red As String = ""
            If unidades.TryGetValue(resultado.Substring(0, 2), red) AndAlso red <> "" Then resultado = red.TrimEnd("\"c) & resultado.Substring(2)
        End If
        Return resultado.TrimEnd("\"c)
    End Function

    Private Shared Function Decodificar(valor As String) As String
        Return System.Text.Encoding.UTF8.GetString(System.Convert.FromBase64String(valor))
    End Function

    Private Sub CargarRelaciones(destino As String)
        Dim resultado As New DatosUsos()
        Try
            ' Resuelve unidades una sola vez, siempre fuera del hilo de la interfaz.
            For Each unidad As String In System.Environment.GetLogicalDrives()
                Dim largo As Integer = 32768
                Dim buffer As New System.Text.StringBuilder(largo)
                If WNetGetConnection(unidad.Substring(0, 2), buffer, largo) = 0 Then resultado.Unidades(unidad.Substring(0, 2)) = buffer.ToString()
            Next
            Dim archivos As String() = System.IO.Directory.GetFiles(destino, "IndiceBuscador_*.txt")
            If archivos.Length = 0 Then resultado.ErrorCarga = "Sin indices"
            For Each archivo As String In archivos
                If Cancelada() Then Return
                Dim usos As String = archivo & ".usos"
                If Not System.IO.File.Exists(usos) Then
                    resultado.Parcial = True
                    Continue For
                End If
                Try
                    ' Primero valida el archivo completo; nunca publica medio archivo.
                    Dim temporal As New System.Collections.Generic.Dictionary(Of String, System.Collections.Generic.HashSet(Of String))(System.StringComparer.OrdinalIgnoreCase)
                    Using lector As New System.IO.StreamReader(usos, System.Text.Encoding.UTF8)
                        Dim cabecera As String = lector.ReadLine()
                        If cabecera Is Nothing OrElse (Not cabecera.StartsWith("#USOS1" & vbTab) AndAlso Not cabecera.StartsWith("#USOS2" & vbTab)) Then Throw New System.Exception("Formato de relaciones no reconocido")
                        While Not lector.EndOfStream
                            If Cancelada() Then Return
                            Dim linea As String = lector.ReadLine()
                            Dim partes As String() = linea.Split(ChrW(9))
                            If partes(0) = "E" Then
                                resultado.Parcial = True
                            ElseIf partes(0) = "R" Then
                                If partes.Length <> 3 Then Throw New System.Exception("Relacion incompleta")
                                Dim padre As String = Clave(Decodificar(partes(1)), resultado.Unidades)
                                Dim hijo As String = Clave(Decodificar(partes(2)), resultado.Unidades)
                                If Not temporal.ContainsKey(hijo) Then temporal(hijo) = New System.Collections.Generic.HashSet(Of String)(System.StringComparer.OrdinalIgnoreCase)
                                temporal(hijo).Add(padre)
                            End If
                        End While
                    End Using
                    For Each par As System.Collections.Generic.KeyValuePair(Of String, System.Collections.Generic.HashSet(Of String)) In temporal
                        If Not resultado.Padres.ContainsKey(par.Key) Then resultado.Padres(par.Key) = New System.Collections.Generic.HashSet(Of String)(System.StringComparer.OrdinalIgnoreCase)
                        resultado.Padres(par.Key).UnionWith(par.Value)
                    Next
                    resultado.IndicesLeidos += 1
                    If System.IO.File.GetLastWriteTimeUtc(archivo) > System.IO.File.GetLastWriteTimeUtc(usos) Then resultado.Parcial = True
                Catch
                    resultado.Parcial = True
                End Try
            Next
        Catch ex As System.Exception
            resultado.Parcial = True
            resultado.ErrorCarga = ex.Message
        Finally
            SyncLock bloqueo
                If Not cerrado Then
                    terminado = resultado : carpetaTerminada = destino
                End If
                carga = False
            End SyncLock
        End Try
    End Sub

    Private Shared Function Ancestros(clavePieza As String, indice As DatosUsos) As System.Collections.Generic.HashSet(Of String)
        If indice.Respuestas.ContainsKey(clavePieza) Then Return indice.Respuestas(clavePieza)
        Dim padres As New System.Collections.Generic.HashSet(Of String)(System.StringComparer.OrdinalIgnoreCase)
        Dim cola As New System.Collections.Generic.Queue(Of String)
        cola.Enqueue(clavePieza)
        While cola.Count > 0
            Dim actual As String = cola.Dequeue()
            If Not indice.Padres.ContainsKey(actual) Then Continue While
            For Each padre As String In indice.Padres(actual)
                If Not String.Equals(padre, clavePieza, System.StringComparison.OrdinalIgnoreCase) AndAlso padres.Add(padre) Then cola.Enqueue(padre)
            Next
        End While
        indice.Respuestas(clavePieza) = padres
        Return padres
    End Function

    Private Sub AjustarListaEnsamblajes(sender As Object, e As System.EventArgs)
        If listaEnsamblajes Is Nothing OrElse listaEnsamblajes.Columns.Count < 2 Then Return
        Dim disponible As Integer = listaEnsamblajes.Width - 8
        If disponible < 160 Then Return
        listaEnsamblajes.Columns(0).Width = 130
        listaEnsamblajes.Columns(1).Width = disponible - 130
        If colFichero IsNot Nothing Then colFichero.Width = System.Math.Max(60, disponible - 136)
    End Sub

    Private Sub MostrarMensaje(texto As String)
        listaEnsamblajes.BeginUpdate()
        Try
            listaEnsamblajes.Items.Clear()
            Dim elemento As New System.Windows.Forms.ListViewItem(texto)
            elemento.SubItems.Add("")
            elemento.Tag = Nothing
            listaEnsamblajes.Items.Add(elemento)
        Finally
            listaEnsamblajes.EndUpdate()
        End Try
        If detalle IsNot Nothing Then detalle.Text = ""
        If botonAbrir IsNot Nothing Then botonAbrir.Enabled = False
    End Sub

    Private Function CodigoEnsamblaje(ruta As String) As String
        Dim nombre As String = System.IO.Path.GetFileNameWithoutExtension(ruta)
        Dim coincidencia As System.Text.RegularExpressions.Match = _
            System.Text.RegularExpressions.Regex.Match(nombre, "^[A-Za-z]*\d+")
        Return If(coincidencia.Success, coincidencia.Value.ToUpperInvariant(), nombre)
    End Function

    Private Sub OnEnsamblajeSeleccionado(sender As Object, e As System.EventArgs)
        If listaEnsamblajes.SelectedItems.Count = 0 OrElse listaEnsamblajes.SelectedItems(0).Tag Is Nothing Then
            detalle.Text = ""
            botonAbrir.Enabled = False
            Return
        End If
        Dim ruta As String = listaEnsamblajes.SelectedItems(0).Tag.ToString()
        detalle.Text = System.IO.Path.GetDirectoryName(ruta)
        botonAbrir.Enabled = True
    End Sub

    Private Sub MostrarSeleccion()
        If seleccion.Count = 0 Then
            estado.Text = "ENSAMBLAJES VINCULADOS"
            MostrarMensaje("Selecciona una pieza.")
            Return
        End If
        If datos Is Nothing Then
            estado.Text = "ENSAMBLAJES VINCULADOS"
            MostrarMensaje("Cargando indice de relaciones...")
            Return
        End If
        If datos.IndicesLeidos = 0 Then
            estado.Text = "SIN RELACIONES DISPONIBLES"
            MostrarMensaje(If(datos.ErrorCarga <> "", "No se pudo cargar el indice.", "Falta generar el indice de relaciones."))
            Return
        End If

        Dim total As New System.Collections.Generic.HashSet(Of String)(System.StringComparer.OrdinalIgnoreCase)
        For Each pieza As String In seleccion
            Try
                total.UnionWith(Ancestros(Clave(pieza, datos.Unidades), datos))
            Catch
                estado.Text = "SELECCION NO VALIDA"
                MostrarMensaje("Selecciona un archivo del listado.")
                Return
            End Try
        Next
        If total.Count = 0 Then
            estado.Text = "ENSAMBLAJES VINCULADOS: 0" & If(datos.Parcial, "  (indice parcial)", "")
            MostrarMensaje(If(datos.Parcial, "Sin coincidencias; indice incompleto.", "Sin ensamblajes en el indice."))
            Return
        End If

        Dim rutas As New System.Collections.Generic.List(Of String)(total)
        rutas.Sort(Function(a As String, b As String) _
            System.StringComparer.OrdinalIgnoreCase.Compare(CodigoEnsamblaje(a), CodigoEnsamblaje(b)))
        listaEnsamblajes.BeginUpdate()
        Try
            listaEnsamblajes.Items.Clear()
            For Each ruta As String In rutas
                Dim elemento As New System.Windows.Forms.ListViewItem(CodigoEnsamblaje(ruta))
                elemento.SubItems.Add(System.IO.Path.GetFileName(ruta))
                elemento.Tag = ruta
                listaEnsamblajes.Items.Add(elemento)
            Next
            If listaEnsamblajes.Items.Count > 0 Then listaEnsamblajes.Items(0).Selected = True
        Finally
            listaEnsamblajes.EndUpdate()
        End Try
        estado.Text = "ENSAMBLAJES VINCULADOS: " & total.Count.ToString() & _
            If(datos.Parcial, "  (indice parcial)", "")
    End Sub

    Private Sub OnTeclaEnsamblajes(sender As Object, e As System.Windows.Forms.KeyEventArgs)
        If e.KeyCode = System.Windows.Forms.Keys.Enter Then
            AbrirEnsamblajesSeleccionados(sender, e)
            e.Handled = True : e.SuppressKeyPress = True
        End If
    End Sub

    Private Sub AbrirEnsamblajesSeleccionados(sender As Object, e As System.EventArgs)
        If AperturaInventorSegura.EnCurso Then Return
        If oApp Is Nothing OrElse listaEnsamblajes.SelectedItems.Count = 0 Then Return
        Dim rutas As New System.Collections.Generic.List(Of String)
        For Each elemento As System.Windows.Forms.ListViewItem In listaEnsamblajes.SelectedItems
            If elemento.Tag IsNot Nothing Then rutas.Add(elemento.Tag.ToString())
        Next
        If rutas.Count = 0 Then Return
        Dim errores As New System.Collections.Generic.List(Of String)
        Dim ventana As System.Windows.Forms.Form = Me.FindForm()
        Dim visibleAnterior As Boolean = ventana IsNot Nothing AndAlso ventana.Visible
        Try
            If visibleAnterior Then ventana.Hide()
            For Each ruta As String In rutas
                Try
                    AperturaInventorSegura.Abrir(oApp, ruta)
                Catch ex As System.Exception
                    errores.Add(ex.Message)
                End Try
            Next
        Finally
            If visibleAnterior AndAlso Not ventana.IsDisposed Then ventana.Show()
        End Try
        If Me.IsDisposed Then Return
        If errores.Count > 0 Then
            estado.Text = "NO SE PUDIERON ABRIR " & errores.Count.ToString() & " ENSAMBLAJE(S)"
            System.Windows.Forms.MessageBox.Show("No se pudieron abrir algunos ensamblajes:" & _
                vbCrLf & vbCrLf & String.Join(vbCrLf & vbCrLf, errores.ToArray()), _
                "Error al abrir", System.Windows.Forms.MessageBoxButtons.OK, _
                System.Windows.Forms.MessageBoxIcon.Error)
        End If
    End Sub
End Class


' Apertura comun para piezas, planos y ensamblajes. Solo en el hilo de interfaz.
'
' v7.9.2: una ruta vacia ya no aborta la apertura.
'   Inventor puede tener abiertos documentos sin guardar (Pieza1, un plano
'   recien creado...) cuyo FullFileName es "". Al recorrer los documentos
'   visibles, GetFullPath("") lanzaba "The path is empty" y fallaba la
'   apertura de cualquier fichero que ya estuviera cargado en memoria sin
'   ventana, por ejemplo como referencia de un ensamblaje abierto. Por eso
'   fallaba solo con algunos ficheros. RutaRed devuelve ahora "" para rutas
'   vacias o no normalizables, y toda comparacion pasa por MismaRuta, que
'   nunca considera iguales dos rutas vacias.
Public Class AperturaInventorSegura
    Private Shared abriendo As Boolean = False

    Private Declare Unicode Function WNetGetConnection Lib "mpr.dll" Alias "WNetGetConnectionW" ( _
        localName As String, remoteName As System.Text.StringBuilder, ByRef length As Integer) As Integer

    Public Shared ReadOnly Property EnCurso As Boolean
        Get
            Return abriendo
        End Get
    End Property

    ' Ruta completa con la unidad mapeada sustituida por su UNC. Devuelve ""
    ' si la ruta esta vacia o no se puede normalizar; nunca lanza.
    Private Shared Function RutaRed(ruta As String) As String
        If String.IsNullOrWhiteSpace(ruta) Then Return ""
        Dim completa As String = ""
        Try
            completa = System.IO.Path.GetFullPath(ruta.Trim())
        Catch
            Return ""
        End Try
        If completa.Length >= 3 AndAlso completa(1) = ":"c Then
            Try
                Dim largo As Integer = 32768
                Dim buffer As New System.Text.StringBuilder(largo)
                If WNetGetConnection(completa.Substring(0, 2), buffer, largo) = 0 Then
                    Return buffer.ToString().TrimEnd("\"c) & completa.Substring(2)
                End If
            Catch
            End Try
        End If
        Return completa
    End Function

    ' True solo si la ruta de un documento coincide con la ruta buscada. Un
    ' documento sin guardar (ruta vacia) nunca coincide con nada.
    Private Shared Function MismaRuta(rutaDocumento As String, red As String) As Boolean
        If red = "" Then Return False
        Dim otra As String = RutaRed(rutaDocumento)
        If otra = "" Then Return False
        Return String.Equals(otra, red, System.StringComparison.OrdinalIgnoreCase)
    End Function

    Public Shared Sub Abrir(app As Inventor.Application, ruta As String)
        If app Is Nothing Then Throw New System.InvalidOperationException("Inventor no esta disponible.")
        If abriendo Then Throw New System.InvalidOperationException("Ya hay una apertura en curso.")
        abriendo = True
        Dim silencioAnterior As Boolean = False
        Dim restaurarSilencio As Boolean = False
        Dim rutaOriginal As String = ruta
        Dim rutaIntentada As String = ruta
        Dim fase As String = "Preparar ruta"
        Try
            If String.IsNullOrWhiteSpace(ruta) Then
                Throw New System.IO.FileNotFoundException("No se ha indicado ningun fichero.")
            End If
            rutaOriginal = System.IO.Path.GetFullPath(ruta.Trim())
            rutaIntentada = rutaOriginal
            Dim red As String = RutaRed(rutaOriginal)
            If red = "" Then red = rutaOriginal

            Dim existente As Inventor.Document = Nothing
            ' P:\ y su UNC son el mismo archivo; no lo abras como dos documentos.
            fase = "Buscar documento ya cargado"
            For Each doc As Inventor.Document In app.Documents
                Try
                    If MismaRuta(doc.FullFileName, red) Then
                        existente = doc
                        rutaIntentada = doc.FullFileName
                        Exit For
                    End If
                Catch
                    ' Un documento que no deja leer su ruta no es el buscado.
                End Try
            Next
            If existente Is Nothing AndAlso Not System.IO.File.Exists(rutaOriginal) Then
                Throw New System.IO.FileNotFoundException("Archivo no accesible.", rutaOriginal)
            End If
            silencioAnterior = app.SilentOperation
            restaurarSilencio = True
            app.SilentOperation = False

            ' Activa solo si YA tiene ventana. Un documento cargado como referencia
            ' o por el indexador necesita Open(..., True) antes de Activate.
            If existente IsNot Nothing Then
                fase = "Comprobar documento visible"
                Dim visibleEncontrado As Inventor.Document = Nothing
                For Each visible As Inventor.Document In app.Documents.VisibleDocuments
                    Try
                        If MismaRuta(visible.FullFileName, red) Then
                            visibleEncontrado = visible
                            Exit For
                        End If
                    Catch
                        ' Documentos sin guardar o sin ruta legible: se ignoran.
                    End Try
                Next
                If visibleEncontrado IsNot Nothing Then
                    fase = "Activar documento visible"
                    visibleEncontrado.Activate()
                    Return
                End If
            End If

            fase = "Abrir documento visible"
            Dim abierto As Inventor.Document = Nothing
            Try
                abierto = app.Documents.Open(rutaIntentada, True)
            Catch ex As System.Runtime.InteropServices.COMException
                ' Solo reintenta E_FAIL con el alias UNC real de Windows.
                ' No reintenta con otro alias un documento que ya estaba cargado.
                If existente IsNot Nothing OrElse ex.ErrorCode <> -2147467259 OrElse _
                        String.Equals(rutaOriginal, red, System.StringComparison.OrdinalIgnoreCase) OrElse _
                        Not System.IO.File.Exists(red) Then Throw
                rutaIntentada = red
                fase = "Abrir por ruta de red"
                abierto = app.Documents.Open(rutaIntentada, True)
            End Try
            If abierto Is Nothing Then Throw New System.InvalidOperationException("Inventor no devolvio un documento.")
            fase = "Activar documento abierto"
            abierto.Activate()
        Catch ex As System.Exception
            Dim proyecto As String = "No disponible"
            Try
                proyecto = app.DesignProjectManager.ActiveDesignProject.FullFileName
            Catch
            End Try
            Throw New System.InvalidOperationException( _
                "Archivo: " & rutaOriginal & vbCrLf & _
                "Ruta utilizada: " & rutaIntentada & vbCrLf & _
                "Operacion: " & fase & vbCrLf & _
                "Proyecto: " & proyecto & vbCrLf & _
                "Detalle: " & ex.ToString(), ex)
        Finally
            Try
                If restaurarSilencio Then app.SilentOperation = silencioAnterior
            Finally
                abriendo = False
            End Try
        End Try
    End Sub
End Class
